--******************************************************************************
-- Filename:    1201v0315r-NewAuxIO.mib
-- Source:      
--              
-- Description: 
--              
-- MIB Revision History:
-- 06/14/22     Finalized fixes for all compilation issues
--
--Copyright 2010 by the American Association of State Highway and
--Transportation Officials (AASHTO), the Institute of Transportation Engineers
--(ITE), and the National Electrical Manufacturers Association (NEMA).  All
--intellectual property rights, including, but not limited to, the rights of
--reproduction in whole or in part in any form, translation into other
--languages and display are reserved by the copyright owners under the laws of
--the United States of America, the Universal Copyright Convention, the Berne
--Convention, and the International and Pan American Copyright Conventions.
--Except for the MIB, Do not copy without written permission of either AASHTO,
--ITE, or NEMA.
--
--                     Joint NEMA, AASHTO, and ITE
--                  NTCIP Management Information Base
--                        DISTRIBUTION NOTICE
--
--To the extent and in the limited event these materials are distributed by
--AASHTO/ITE/NEMA in the form of a Management Information Base ("MIB"), 
--AASHTO/ITE/NEMA extends the following permissions:
--
-- (i) you may make and/or distribute unlimited copies (including derivative
--works) of the MIB, including copies for commercial distribution, provided
--that (a) each copy you make and/or distribute contains this Notice and (b)
--each derivative work of the MIB uses the same module name followed by "-",
--followed by your Internet Assigned Number Authority (IANA)-assigned 
--enterprise number;
--(ii) use of the MIB is restricted in that the syntax field may be modified
--only to reflect a more restrictive sub-range or enumerated values;
--(iii) the description field may be modified but only to the extent that:
--(a) only those bit values or enumerated values that are supported are
--listed; and (b) the more restrictive subrange is expressed.
--
--These materials are delivered "AS IS" without any warranties as to their use
--or performance.
--
--AASHTO/ITE/NEMA AND THEIR SUPPLIERS DO NOT WARRANT THE PERFORMANCE OR
--RESULTS YOU MAY OBTAIN BY USING THESE MATERIALS.  AASHTO/ITE/NEMA AND THEIR
--SUPPLIERS MAKE NO WARRANTIES, EXPRESS OR IMPLIED, AS TO NONINFRINGEMENT OF
--THIRD PARTY RIGHTS, MERCHANTABILITY, OR FITNESS FOR ANY PARTICULAR PURPOSE.
--IN NO EVENT WILL AASHTO, ITE OR NEMA OR THEIR SUPPLIERS BE LIABLE TO YOU OR
--ANY THIRD PARTY FOR ANY CLAIM OR FOR ANY CONSEQUENTIAL, INCIDENTAL OR
--SPECIAL DAMAGES, INCLUDING ANY LOST PROFITS OR LOST SAVINGS, ARISING FROM
--YOUR REPRODUCTION OR USE OF THESE MATERIALS, EVEN IF AN AASHTO, ITE, OR NEMA
--REPRESENTATIVE HAS BEEN ADVISED OF THE POSSIBILITY OF SUCH DAMAGES.  Some
--states or jurisdictions do not allow the exclusion or limitation of
--incidental, consequential or special damages, or the exclusion of implied
--warranties, so the above limitations may not apply to you.
--
--Use of these materials does not constitute an endorsement or affiliation by
--or between AASHTO, ITE, or NEMA and you, your company, or your products and
--services.
--
--NTCIP is a trademark of AASHTO/ITE/NEMA.
--******************************************************************************
--2.9 NEW AUXILIARY I/O OBJECTS IN NTCIP 1201 V03
AuxIOv2-1201 DEFINITIONS ::= BEGIN
IMPORTS
 OBJECT-TYPE
 FROM RFC-1212 
 DisplayString
 FROM RFC1213-MIB
 global
 FROM NTCIP8004v02;
 
auxIOv2 OBJECT IDENTIFIER ::= { global 7}
-- <Object Identifier> 1.3.6.1.4.1.1206.4.2.6.7
-- This node is an identifier used to group all objects supporting auxiliary
-- I/O functions
--
-- NOTE: The auxiliary I/O management objects listed in NTCIP 1201 v03 define a
-- mechanism for the support of unspecified I/O for an NTCIP device.
-- The agency or device specifications define the intended operation
-- of these ports.
--
-- NOTE: NTCIP 1201 v01 defined functionality of these
-- objects under the experimental node. For the purposes of
-- backward compatibility, the names of these objects, originally defined in
-- NTCIP 1201 v02, have been modified to eliminate any conflicts/
-- confusion with the objects defined under the experimental node. For those
-- agents that may support these objects and those originally defined under
-- the experimental node (see Section 2.10), the object definitions aretreated
-- as aliases such that a write to an object in one group acts as write
-- to the corresponding object in the other group. As aliases, a read of an
-- object in this group is equivalent to a read of the corresponding object in
-- the auxIO group.
--
-- NOTE:
-- Early NTCIP deployments included the Aux I/O objects defined in NTCIP
-- 1203v01 located under an experimental node. These objects were moved to a
-- permanent node with the release of NTCIP 1201 v02 and given new
-- names. This can create confusion and backward compatibility issues.
-- As noted in the object definition, both sets of objects refer to the
-- same functions within the device; hence, both sets of objects cause the
-- same device action or provide the same device status.
-- Agency specifications that do NOT require support for the Aux I/O
-- objects under the experimental node should explicitly exclude the support
-- for these experimental objects (which have been deprecated) for
-- backward compatibility. Support of the Aux I/O objects under the
-- permanent node identified in NTCIP 1201 v03 may be optional
-- or mandatory depending on agency or device specifications.
--
--Use the PRL to exclude support of NTCIP 1201 v01-defined aux I/O objects.
--
-- The relationship between mandatory and optional support of NTCIP v01 (experimental)
-- and NTCIP v02 objects is unique to the Aux I/O objects.

--2.9.1 Maximum Number of Digital Auxiliary I/Os Parameter
maxAuxIOv2TableNumDigitalPorts OBJECT-TYPE
SYNTAX INTEGER (0..255)
ACCESS read-only
STATUS mandatory
DESCRIPTION
"<Definition> The number of rows contained in the 'auxIOv2Table' with the auxIOv2PortType set to 'digital'.
<Object Identifier> 1.3.6.1.4.1.1206.4.2.6.7.1"
::= { auxIOv2 1} 

--2.9.2 Maximum Number of Analog Auxiliary I/Os Parameter
maxAuxIOv2TableNumAnalogPorts OBJECT-TYPE
SYNTAX INTEGER (0..255)
ACCESS read-only
STATUS mandatory
DESCRIPTION
"<Definition>The number of rows contained in the 'auxIOv2Table' with the auxIOv2PortType set to 'analog'.
<Unit>port
<Object Identifier> 1.3.6.1.4.1.1206.4.2.6.7.2"
::= {auxIOv2 2}

--2.9.3 Auxiliary I/O Table Parameter
auxIOv2Table OBJECT-TYPE
SYNTAX SEQUENCE OF AuxIOv2Entry
ACCESS not-accessible
STATUS mandatory
DESCRIPTION
"<Definition>A table providing the means to access any non-mission-critical or non-safety-related auxiliary I/O of the controller, including reading inputs and setting outputs. The number of rows in this table equals the sum of the values of the 'maxAuxIOv2TableNumDigitalPorts' and 'maxAuxIOv2TableNumAnalogPorts' objects.
This table shall not be used to control or monitor any safety related equipment. The electrical levels used by the ports are not standardized by auxIOv2Table objects; such information should be contained in the hardware manual.
<TableType> static
<Object Identifier> 1.3.6.1.4.1.1206.4.2.6.7.3"
::= { auxIOv2 3}

auxIOv2Entry OBJECT-TYPE
SYNTAX AuxIOv2Entry
ACCESS not-accessible
STATUS mandatory
DESCRIPTION
"<Definition>Parameters of the auxiliary I/O table.
<Object Identifier> 1.3.6.1.4.1.1206.4.2.6.7.3.1"
INDEX {auxIOv2PortType, auxIOv2PortNumber}
::={auxIOv2Table 1}

AuxIOv2Entry ::= SEQUENCE {
	auxIOv2PortType INTEGER,
	auxIOv2PortNumber INTEGER,
	auxIOv2PortDescription DisplayString,
	auxIOv2PortResolution INTEGER,
	auxIOv2PortValue INTEGER,
	auxIOv2PortDirection INTEGER,
	auxIOv2PortLastCommandedState INTEGER } 
	
--2.9.3.1 Auxiliary Port Type Parameter
auxIOv2PortType OBJECT-TYPE
SYNTAX INTEGER{
	other (1),
	analog (2),
	digital (3)} 
ACCESS read-only
STATUS mandatory
DESCRIPTION
"<Definition>Indicates the type of auxiliary I/O, which can be analog or digital.
<Information> From NTCIP 1201 v01 to NTCIP v02 of these objects, it was determined that ports are either digital, analog, or other.
<Object Identifier> 1.3.6.1.4.1.1206.4.2.6.7.3.1.1"
::= {auxIOv2Entry 1} 

--2.9.3.2 Auxiliary Port Number Parameter
auxIOv2PortNumber OBJECT-TYPE
SYNTAX INTEGER (1..255)
ACCESS read-only
STATUS mandatory
DESCRIPTION
"<Definition>Indicates the port number for the associated port type. Port numbers are used sequentially from one to max for each port type. There can be a port 1 for analog port and port 1 for digital port.
 <Object Identifier> 1.3.6.1.4.1.1206.4.2.6.7.3.1.2"
::= {auxIOv2Entry 2}

--2.9.3.3 Auxiliary Description Parameter
auxIOv2PortDescription OBJECT-TYPE
SYNTAX DisplayString (SIZE (0..255))
ACCESS read-write
STATUS mandatory
DESCRIPTION
"<Definition>Informational text field describing the device at the associated auxiliary I/O.
<Informative> In NTCIP 1203 v01, the SYNTAX SIZE was listed as (0..50). In NTCIP 1201 v02 and NTCIP 1201 v03, this was changed to (0..255).
<Object Identifier> 1.3.6.1.4.1.1206.4.2.6.7.3.1.3"
::= {auxIOv2Entry 3}

--2.9.3.4 Auxiliary Resolution Parameter
auxIOv2PortResolution OBJECT-TYPE
SYNTAX INTEGER (1..255)
ACCESS read-only
STATUS mandatory
DESCRIPTION
"<Definition>Defines number of bits used for the IO-port (e.g. width of digital, resolution of analog). Thus, this feature allows the digital monitoring (via NTCIP) of an analog port on  the agent.
<Informative> In NTCIP 1203 v01, ACCESS was listed as read-write; however, in NTCIP 1201 v03, ACCESS changed to read-only. This changed because resolution is fixed by the hardware implementation and cannot be changed by the management station.
The SYNTAX also changed from NTCIP 1201 v02 to NTCIP 1201 v03; it is now as it was originally under the experimental node defined in NTCIP 1203v01. This changed to address backward compatibility and the 'aliasing' between the version 1 objects (see Section 2.10) and the Version 02 objects.
<Unit>bit
<Object Identifier> 1.3.6.1.4.1.1206.4.2.6.7.3.1.4"
::= {auxIOv2Entry 4} 

--2.9.3.5 Auxiliary Value Parameter
auxIOv2PortValue OBJECT-TYPE
SYNTAX INTEGER (0..4294967295)
ACCESS read-write
STATUS mandatory
DESCRIPTION
"<Definition>For input or bidirectional ports, this contains the current value of the input. For output ports, this is the last commanded value of the port. A genError shall be generated, if  this object is set and the port is an input. The actual value exchanged shall not exceed [2^(auxIOv2PortResolution) – 1]; any SET operation to a value in excess of this number shall result in a genErr, and any GET response in excess of this value shall be considered erroneous.
<Object Identifier> 1.3.6.1.4.1.1206.4.2.6.7.3.1.5"
::= {auxIOv2Entry 5}

--2.9.3.6 Auxiliary Port Direction Parameter
auxIOv2PortDirection OBJECT-TYPE
SYNTAX INTEGER {
	output (1),
	input (2),
	bidirectional (3)}
ACCESS read-only
STATUS mandatory
DESCRIPTION
"<Definition>Indicates whether state of this port can be set (output), read (input) or both (bidirectional).
<Object Identifier> 1.3.6.1.4.1.1206.4.2.6.7.3.1.6"
::= {auxIOv2Entry 6}

--2.9.3.7 Auxiliary Port Last Commanded State Parameter
auxIOv2PortLastCommandedState OBJECT-TYPE
SYNTAX INTEGER (0..4294967295)
ACCESS read-only
STATUS mandatory
DESCRIPTION
"<Definition>For bi-directional ports, this object indicates the last state to which the auxIOv2PortValue object was set. For output ports, this value shall always be equal to the auxIOv2PortValue object. For input ports, this value shall always be zero (0).
<Object Identifier> 1.3.6.1.4.1.1206.4.2.6.7.3.1.7"
::= {auxIOv2Entry 7}
END -- AuxIOv2-1201 DEFINITIONS
