-- A.7 TMP REPORT MIB Header
-- Filename:     1103v0352-Report.MIB
-- Description:  This MIB defines various objects related to managing 
--               event information for the purpose of logging data within the 
--               device. 
--               Specifically, these include objects related to: 
--               (a) managing event information that can be logged in the
--               device
--               This MIB replaces portions of TMIB-II.
--
-- MIB Revision History:
-- 08/01/96   Original standard approved
-- 01/01/98   Preliminary Release of TS 3.2 TMIB MIB formatted for 80
--               columns and no TABs
-- 01/07/98   Replaced some missed TABs with spaces
-- 07/08/98   Added Copyright Notice
-- 10/07/98   Amendment 1
-- 03/09/00   Removed all the special edits to that were done to use the 
--               SMIC Compiler
--               Defined DisplayString to eliminate reference to RFC 1212
--               END is still left "Dynamic Object Data" group
--               Changed filename and updated copyright years
--               Updated the MIB to Amendment 1
-- 08/09/00   Modified header format and wording of copyright and MIB
-- 11/16/01   Added objects for sfmp and stmp statistics
--               Moved security node into this MIB from NTCIP 1201
--               Added objects to support logical names
--               Renamed the module to NTCIP1103-A-2002 from TMIB-II
--               Renamed the text name to Transportation Management 
--               Protocols MIB from Transportation MIB
--               Changed STATUS of all objects to optional to reflect new 
--               conformance rules being defined in NTCIP 8004
-- 06/08/04   Moved report node into this MIB from NTCIP 1201
-- 09/27/04   Changed name of file.
-- 10/11/04   Per KLV e-mails 10/08/04 updated version and 
--               Changed Index on logicalNameTranslation-index 
--                  from (0..255) to (1..255)
--                Changed all STATUS optional to mandatory
-- 06/13/05   Updated filename.
-- 08/09/05   Added object definitions for Trap Management, Watch Block Objects
--               Updated filename; re-instantiated the OIDs for the 
--               13 dynamic objects.
-- 04/19/06   Broke the various logical groupings of objects into separate
--               MIBs to allow for separate compiling for various deployment
--               needs.
-- 12/14/07   Changed the name of this MIB only to reflect the version number.
-- 11/07/16   Changed the name of this MIB only to reflect the version number.
-- 12/03/16   Modified to correct issues found in compiling MIBs with SMICng v2.2.07
--
--              DISTRIBUTION NOTICE
--Copyright 1996 - 2016 by the American Association of State Highway and
--Transportation Officials (AASHTO), the Institute of Transportation Engineers
--(ITE), and the National Electrical Manufacturers Association (NEMA). All
--intellectual property rights, including, but not limited to, the rights of
--reproduction in whole or in part in any form, translation into other
--languages and display are reserved by the copyright owners under the laws of
--the United States of America, the Universal Copyright Convention, the Berne
--Convention, and the International and Pan American Copyright Conventions.
--Except for the MIB, Do not copy without written permission of either AASHTO,
--ITE, or NEMA.
--
--                     Joint NEMA, AASHTO, and ITE
--                  NTCIP Management Information Base
--                        DISTRIBUTION NOTICE
--
--To the extent and in the limited event these materials are distributed by
--AASHTO/ITE/NEMA in the form of a Management Information Base ("MIB"), 
--AASHTO/ITE/NEMA extends the following permissions:
--
--(i) you may make and/or distribute unlimited copies (including derivative
--works) of the MIB, including copies for commercial distribution, provided
--that (a) each copy you make and/or distribute contains this Notice and (b)
--each derivative work of the MIB uses the same module name followed by "-",
--followed by your Internet Assigned Number Authority (IANA)-assigned 
--enterprise number;
--(ii) use of the MIB is restricted in that the syntax field may be modified
--only to reflect a more restrictive sub-range or enumerated values;
--(iii) the description field may be modified but only to the extent that:
--(a) only those bit values or enumerated values that are supported are
--listed; and (b) the more restrictive subrange is expressed.
--
--These materials are delivered "AS IS" without any warranties as to their use
--or performance.
--
--AASHTO/ITE/NEMA AND THEIR SUPPLIERS DO NOT WARRANT THE PERFORMANCE OR
--RESULTS YOU MAY OBTAIN BY USING THESE MATERIALS. AASHTO/ITE/NEMA AND THEIR
--SUPPLIERS MAKE NO WARRANTIES, EXPRESS OR IMPLIED, AS TO NONINFRINGEMENT OF
--THIRD PARTY RIGHTS, MERCHANTABILITY, OR FITNESS FOR ANY PARTICULAR PURPOSE.
--IN NO EVENT WILL AASHTO, ITE OR NEMA OR THEIR SUPPLIERS BE LIABLE TO YOU OR
--ANY THIRD PARTY FOR ANY CLAIM OR FOR ANY CONSEQUENTIAL, INCIDENTAL OR
--SPECIAL DAMAGES, INCLUDING ANY LOST PROFITS OR LOST SAVINGS, ARISING FROM
--YOUR REPRODUCTION OR USE OF THESE MATERIALS, EVEN IF AN AASHTO, ITE, OR NEMA
--REPRESENTATIVE HAS BEEN ADVISED OF THE POSSIBILITY OF SUCH DAMAGES. Some
--states or jurisdictions do not allow the exclusion or limitation of
--incidental, consequential or special damages, or the exclusion of implied
--warranties, so the above limitations may not apply to you.
--
--Use of these materials does not constitute an endorsement or affiliation by
--or between AASHTO, ITE, or NEMA and you, your company, or your products and
--services.
--
--NTCIP is a trademark of AASHTO/ITE/NEMA.
--****************************************************************************

NTCIP1103v0352-Report DEFINITIONS ::= BEGIN

IMPORTS
      Counter, Opaque, null
            FROM RFC1155-SMI
      OBJECT-TYPE
            FROM RFC-1212
      global
            FROM NTCIP8004-2008;
-- EXPORTS EVERYTHING

-- A.7.1 Report Parameter Node
globalReport  OBJECT IDENTIFIER ::= { global 4 }
--            <Object Identifier> 1.3.6.1.4.1.1206.4.2.6.4

-- This node is an identifier used to organize all objects for 
-- support of report functions that are common to most device types.

-- NOTE—The event class table is presented first to ease 
-- the readability of the standard; however, the node numbers 
-- assigned to this table reflect the original node numbering used 
-- in the original 1996 specification to preserve backwards 
-- compatibility with existing systems.

-- A.7.2 Maximum Event Classes Parameter
maxEventClasses  OBJECT-TYPE
   SYNTAX  INTEGER (1..255)
   ACCESS  read-only
   STATUS  mandatory
   DESCRIPTION
      "<Definition> The object defines the number of rows in the 
        eventClassTable that this device supports. This is a static 
        table. 
      <Unit>EventClass
      <Object Identifier> 1.3.6.1.4.1.1206.4.2.6.4.5
     "
::= { globalReport 5 }

-- A.7.3 Event Class Table
eventClassTable  OBJECT-TYPE
   SYNTAX  SEQUENCE OF EventClassEntry
   ACCESS  not-accessible
   STATUS  mandatory
   DESCRIPTION
      "<Definition>This table is used to configure event logging 
        limits and log table maintenance. 
       <TableType> static
       <Object Identifier> 1.3.6.1.4.1.1206.4.2.6.4.6
      "
::= { globalReport 6 }

eventClassEntry  OBJECT-TYPE
   SYNTAX  EventClassEntry
   ACCESS  not-accessible
   STATUS  mandatory
   DESCRIPTION
      "<Definition>This defines a row in the Event Class Table
       <Object Identifier> 1.3.6.1.4.1.1206.4.2.6.4.6.1
      "
   INDEX { eventClassNumber }
::= { eventClassTable 1 }

EventClassEntry ::= SEQUENCE {
   eventClassNumber        INTEGER,
   eventClassLimit         INTEGER,
   eventClassClearTime     Counter,
   eventClassDescription   OCTET STRING,
   eventClassNumRowsInLog  INTEGER,
   eventClassNumEvents     INTEGER }

-- A.7.3.1 Event Class Number Parameter
eventClassNumber  OBJECT-TYPE
   SYNTAX  INTEGER (1..255)
   ACCESS  read-only
   STATUS  mandatory
   DESCRIPTION
      "<Definition>This is a class value that is to be configured. 
       <Object Identifier> 1.3.6.1.4.1.1206.4.2.6.4.6.1.1
      "
::= { eventClassEntry 1 }

-- A.7.3.2 Event Class Limit Parameter
eventClassLimit  OBJECT-TYPE
   SYNTAX  INTEGER (0..255)
   ACCESS  read-write
   STATUS  mandatory
   DESCRIPTION
      "<Definition>This object specifies the maximum number of 
        events of the associated class to store in the log. Once 
        the limit is reached, the oldest entry of the matching 
        class will be overwritten by any new entry of the same 
        class. If the value of this object is set to a number 
        smaller than the current number of rows within this class 
        in the eventLogTable, then the oldest entries shall be 
        lost/deleted. The sum of all event class limits shall not 
        exceed the maxEventLogSize object; if a SET operation to 
        this object causes the sum of eventClassLimit objects to 
        exceed maxEventLogSize, then the agent shall respond with 
        a genErr. 
        The event cannot be logged if the eventClass has an 
        eventClassLimit of zero (0).
       <Unit>Event
       <Object Identifier> 1.3.6.1.4.1.1206.4.2.6.4.6.1.2
      "
::= { eventClassEntry 2 }

-- A.7.3.3 Event Class Clear Time Parameter
eventClassClearTime OBJECT-TYPE
   SYNTAX  Counter
   ACCESS  read-write
   STATUS  mandatory
   DESCRIPTION
      "<Definition>This object is used to clear multiple event log 
        entries from the eventLogTable. All events of this class 
        that have an eventLogTime equal to or less than this object 
        shall be cleared from the eventLogTable. If this object has 
        a value greater than the current value of globalTime, it 
        shall prevent the logging of any events of this class.
       <Unit>second
       <Object Identifier> 1.3.6.1.4.1.1206.4.2.6.4.6.1.3
      "
   DEFVAL  {0}
::= { eventClassEntry 3 }

-- A.7.3.4 Event Class Description Parameter
eventClassDescription  OBJECT-TYPE
   SYNTAX  OCTET STRING
   ACCESS  read-write
   STATUS  mandatory
   DESCRIPTION
      "<Definition>This object specifies a description of the class 
        in ASCII characters. 
       <Object Identifier> 1.3.6.1.4.1.1206.4.2.6.4.6.1.4
      "
::= { eventClassEntry 4 }

-- A.7.3.5 Event Class Number of Rows in Event Log Table Parameter
eventClassNumRowsInLog  OBJECT-TYPE
   SYNTAX  INTEGER (0..255)
   ACCESS  read-only
   STATUS  mandatory
   DESCRIPTION
      "<Definition>The number of rows for this class that currently 
        exist in the eventLogTable. 
       <Unit>Event
       <Object Identifier> 1.3.6.1.4.1.1206.4.2.6.4.6.1.5
      "
::= { eventClassEntry 5 }

-- A.7.3.6 Class Event Log Counter Parameter
eventClassNumEvents  OBJECT-TYPE
   SYNTAX  INTEGER (0..65535)
   ACCESS  read-only
   STATUS  mandatory
   DESCRIPTION
      "<Definition> This object is a counter that gets incremented 
        every time an event occurs for this class; it shall 
        initialize to zero at power up. The value shall roll over 
        each time it exceeds the maximum of 65535. 
       <Unit>Events
       <Object Identifier> 1.3.6.1.4.1.1206.4.2.6.4.6.1.6
      "
::= { eventClassEntry 6 }

-- A.7.4 Maximum Event Log Configurations Parameter
maxEventLogConfigs  OBJECT-TYPE
   SYNTAX  INTEGER (1..65535)
   ACCESS  read-only
   STATUS  mandatory
   DESCRIPTION
      "<Definition>The number of rows that exist in the static 
        eventLogConfig table for this device. 
       <Unit>EventType
       <Object Identifier> 1.3.6.1.4.1.1206.4.2.6.4.1
      "
::= { globalReport 1}

-- A.7.5 Event Log Configuration Table
eventLogConfigTable  OBJECT-TYPE
   SYNTAX  SEQUENCE OF EventLogConfigEntry
   ACCESS  not-accessible
   STATUS  mandatory
   DESCRIPTION
      "<Definition>A table containing Event Log Configuration 
        information. The number of rows in this table is equal to 
        the maxEventLogConfigs object. This table defines the 
        parameters that the device will monitor to create an event. 
      <TableType> static
      <Object Identifier> 1.3.6.1.4.1.1206.4.2.6.4.2
     "
::= { globalReport 2 }

eventLogConfigEntry  OBJECT-TYPE
   SYNTAX  EventLogConfigEntry
   ACCESS  not-accessible
   STATUS  mandatory
   DESCRIPTION
      "<Definition>This object defines an entry in the event log 
        configuration table. 
       <Object Identifier> 1.3.6.1.4.1.1206.4.2.6.4.2.1
      "
   INDEX { eventConfigID }
::= { eventLogConfigTable 1 }

EventLogConfigEntry ::= SEQUENCE {
   eventConfigID             INTEGER,
   eventConfigClass          INTEGER,
   eventConfigMode           INTEGER,
   eventConfigCompareValue   INTEGER,
   eventConfigCompareValue2  INTEGER,
   eventConfigCompareOID     OBJECT IDENTIFIER,
   eventConfigLogOID         OBJECT IDENTIFIER,
   eventConfigAction         INTEGER,
   eventConfigStatus         INTEGER }

-- A.7.5.1 Event Log Configuration ID Parameter
eventConfigID  OBJECT-TYPE
   SYNTAX  INTEGER (1..65535)
   ACCESS  read-only
   STATUS  mandatory
   DESCRIPTION
      "<Definition>This object contains the row number which is 
        used to identify the event associated with this row in the 
        eventLogConfigTable. The number of event IDs shall not 
        exceed the value indicated in the maxEventLogConfigs object. 
       <Object Identifier> 1.3.6.1.4.1.1206.4.2.6.4.2.1.1
      "
::= { eventLogConfigEntry 1 }

-- A.7.5.2 Event Log Configuration Class Parameter
eventConfigClass  OBJECT-TYPE
   SYNTAX  INTEGER (1..255)
   ACCESS  read-write
   STATUS  mandatory
   DESCRIPTION
      "<Definition>This object contains the class value to assign 
        to the event associated with this row in the event 
        configuration table. This value is used in the event log 
        table to organize various events defined in this table into 
        logical groupings. This value shall not exceed the 
        maxEventClasses object value. 

        NOTE—The event cannot be logged if the EventClass has an 
        eventClassLimit of zero (0). 
       <Object Identifier> 1.3.6.1.4.1.1206.4.2.6.4.2.1.2
      "
   DEFVAL  {1}
::= { eventLogConfigEntry 2 }

-- A.7.5.3 Event Log Configuration Mode Parameter
eventConfigMode  OBJECT-TYPE
   SYNTAX  INTEGER { other (1),
                     onChange (2),
                     greaterThanValue (3),
                     smallerThanValue (4),
                     hysteresisBound (5),
                     periodic (6),
                     andedWithValue (7) }
   ACCESS  read-write
   STATUS  mandatory
   DESCRIPTION
      "<Definition>This object specifies the mode of operation for 
        this event. The modes are defined as follows:
        Value             Description
        other             the event mode of operation is not 
                          described in this standard, refer to the 
                          device manual.
        onChange          create a log entry when the object value 
                          referenced by eventConfigCompareOID 
                          changes. The values of 
                          eventConfigCompareValue and 
                          eventConfigCompareValue2 are ignored in 
                          this mode.
        greaterThanValue  create a log entry when the object value 
                          referenced by eventConfigCompareOID 
                          becomes greater than the value of 
                          eventConfigCompareValue for the time 
                          (tenth seconds) defined by 
                          eventConfigCompareValue2 (zero means 
                          immediate logging).
        smallerThanValue  create a log entry when the object value 
                          referenced by eventConfigCompareOID 
                          becomes less than the value of 
                          eventConfigCompareValue for the time 
                          (tenth seconds) defined by 
                          eventConfigCompareValue2 (zero means 
                          immediate logging).
        hysteresisBound   create a log entry when the object value 
                          referenced by eventConfigCompareOID 
                          becomes less than or greater than the 
                          bound values. The lowerbound value is the 
                          lower value of eventConfigCompareValue and 
                          eventConfigCompareValue2; the upperbound 
                          value is the higher value of the two values. 

                          When the object value becomes greater than 
                          the upper bound value, subsequent logging of 
                          upperbound conditions shall not occur until 
                          the object value becomes less than the 
                          lower bound value. 

                          When the object value becomes less than 
                          the lower bound value, subsequent logging 
                          of lowerbound conditions shall not occur 
                          until the object value becomes greater 
                          than the upper bound value.
        periodic          create a log entry every x seconds, where 
                          x is defined by the value stored in 
                          eventConfigCompareValue. The values stored 
                          in eventConfigCompareValue2 and 
                          eventConfigCompareOID are ignored in this 
                          mode.
        andedWithValue    create a log entry when the object value 
                          referenced by eventConfigCompareOID ANDED 
                          with the value of eventConfigCompareValue 
                          is NOT equal to zero for the time (tenth 
                          seconds) defined by eventConfigCompareValue2 
                          (zero means immediate logging). This allows 
                          monitoring of a specific bit; the condition 
                          becomes true anytime that any one of the 
                          selected bits become true.

       <Object Identifier> 1.3.6.1.4.1.1206.4.2.6.4.2.1.3
      "
   DEFVAL  {onChange}
::= { eventLogConfigEntry 3 }

-- A.7.5.4 Event Log Configuration Compare Value Parameter
eventConfigCompareValue  OBJECT-TYPE
   SYNTAX  INTEGER
   ACCESS  read-write
   STATUS  mandatory
   DESCRIPTION
      "<Definition>This object contains the comparison value to 
        use with eventConfigMode values (greaterThanValue, 
        smallerThanValue, hysteresisBound ). No value within this 
        object is necessary when the eventConfigMode-object has the 
        value onChange (2). 
       <Object Identifier> 1.3.6.1.4.1.1206.4.2.6.4.2.1.4
      "
   DEFVAL  {0}
::= { eventLogConfigEntry 4 }

-- A.7.5.5 Event Log Configuration Compare Value 2 Parameter
eventConfigCompareValue2  OBJECT-TYPE
   SYNTAX  INTEGER
   ACCESS  read-write
   STATUS  mandatory
   DESCRIPTION
      "<Definition>If the eventConfigMode is set to 
        hysteresisBound, this object specifies the second comparison 
        value for the hysteresis. If the eventConfigMode is set to 
        greaterThanValue, smallerThanValue, or andedWithValue, this 
        object specifies the time (in tenths of seconds, +1 tenth / -0 
        tenths) for which the samples used for comparison shall be 
        true prior to the event condition becoming true. If the 
        eventConfigMode is set to onChange or periodic, the value of 
        this object shall be ignored. 

        The amount of time the condition shall be true is measured in 
        tenths of a second. The accuracy of this timer is limited to 
        +1 tenth of a second and –0 tenths of a second. If the event 
        is true for at least the time shown in this parameter +1 
        tenth of a second, the condition shall trigger a log entry. 
        It is recognized that some designs only sample the condition 
        periodically, in which case the condition shall be true for 
        at least the time indicated by this object before the event 
        becomes true and the event shall always become true if the 
        condition is true for a duration equal to the value shown in 
        this object plus 1 tenth of a second.
       <Object Identifier> 1.3.6.1.4.1.1206.4.2.6.4.2.1.5
      "
   DEFVAL  {0}
::= { eventLogConfigEntry 5 }

-- A.7.5.6 Event Log Configuration Compare Object Identifier Parameter
eventConfigCompareOID  OBJECT-TYPE
   SYNTAX  OBJECT IDENTIFIER
   ACCESS  read-write
   STATUS  mandatory
   DESCRIPTION
      "<Definition> This object contains the object identifier 
        which references the value against which the comparison 
        is made. If the eventConfigMode is set to periodic, the 
        value of this object shall be ignored. If the 
        eventConfigMode is set to greaterThanValue, smallerThanValue 
        or hysteresisBound, this object shall reference an object 
        whose SYNTAX resolves to a ranged or unranged INTEGER. As 
        with all other objects that are sub-ranged by a given 
        implementation, an agent should return a badValue error if 
        it receives a set command indicating a OID which is not 
        supported by the implementation or which is not null. 
       <Object Identifier> 1.3.6.1.4.1.1206.4.2.6.4.2.1.6
      "
   DEFVAL  {null}
::= { eventLogConfigEntry 6 }

-- A.7.5.7 Event Log Configuration Log Object Identifier Parameter
eventConfigLogOID  OBJECT-TYPE
   SYNTAX  OBJECT IDENTIFIER
   ACCESS  read-write
   STATUS  mandatory
   DESCRIPTION
      "<Definition>This object contains the object identifier which 
        indicates what value to log when a condition or event occurs 
        (e.g., log the phase display when the watchdog alarm status 
        changes). As with all other objects that are sub-ranged by a 
        given implementation, an agent should return a badValue 
        error if it receives a set command indicating a value which 
        is not supported by the implementation. The valid value 
        range of this object shall not include any values, other 
        than null, that do not correspond to objects that may exist 
        within the agent, although it may be further restricted.

        The valid value range of this object shall not include 
        objects under the following nodes:
           Security - { nema transportation devices global security }
           CHAP - { nema transportation protocols layers chap }

       <Object Identifier> 1.3.6.1.4.1.1206.4.2.6.4.2.1.7
      "
   DEFVAL  {null}
::= { eventLogConfigEntry 7 }

-- A.7.5.8 Event Log Configuration Action Parameter
eventConfigAction  OBJECT-TYPE
  SYNTAX  INTEGER { other (1),
                    disabled (2),
                    log (3) }
   ACCESS  read-write
   STATUS  mandatory
   DESCRIPTION
      "<Definition>The value of this object indicates what action 
        shall take place when this event occurs.
        other    - indicates that the action is other than defined in this standard. This value exists in order to support proprietary event logging mechanisms configured by other means not specified in this standard. If this value is used in a SET request, the agent shall respond with a badValueError.
        disabled - no event log entry shall be generated or recorded due to this event. In an agent complying with NTCIP 1103 v03 or later, this event shall not be used to trigger NTCIP traps, nor to construct NTCIP trap messages.
        log      - an event log entry shall be generated when this event occurs. In an agent complying with NTCIP 1103 v03 and later, this may trigger an NTCIP trap (see the eventConfigID index element of trapTable). If eventConfigClass refers to an eventClassTable row having eventClassLimit = 0, the log entry’s eventLogValue shall be used to construct any necessary trap messages implied by the associated trapTable rows, but the log entry shall then be discarded and not added to the eventLogTable. If the eventClassLimit is greater than zero, the log entry shall be added to the eventLogTable, subject to the constraints imposed by the associated eventConfigClass.

       <Object Identifier> 1.3.6.1.4.1.1206.4.2.6.4.2.1.8
      "
   DEFVAL  {disabled}
::= { eventLogConfigEntry 8 }

-- A.7.5.9 Event Log Configuration Status Parameter
eventConfigStatus  OBJECT-TYPE
   SYNTAX  INTEGER { other (1),
                     disabled (2),
                     log (3),
                     error (4) }
   ACCESS  read-only
   STATUS  mandatory
   DESCRIPTION
      "<Definition>The value of this object indicates the current 
        status of the configured event. Upon setting any object in 
        this row of the eventLogConfigTable, the agent will 
        determine if the setting is valid and will set this object 
        to one of the following states:
        other      indicates that the action is successfully set to 
                   a mode other than that defined in this standard
        disabled   indicates that the action is set to disabled
        log        indicates that the action is successfully set to 
                   the log state after passing consistency checks.
        error      indicates that the requested action could not be 
                   implemented due to a consistency check 
       <Object Identifier> 1.3.6.1.4.1.1206.4.2.6.4.2.1.9
      "
::= { eventLogConfigEntry 9 }

-- A.7.6 Maximum Event Log Size Parameter
maxEventLogSize  OBJECT-TYPE
   SYNTAX  INTEGER (1..65535)
   ACCESS  read-only
   STATUS  mandatory
   DESCRIPTION
      "<Definition>The maximum, fixed number of rows that can be 
        utilized within the eventLogTable. 
       <Unit>Event
       <Object Identifier> 1.3.6.1.4.1.1206.4.2.6.4.3
      "
::= { globalReport 3}

-- A.7.7 Event Log Table 
eventLogTable  OBJECT-TYPE
   SYNTAX  SEQUENCE OF EventLogEntry
   ACCESS  not-accessible
   STATUS  mandatory
   DESCRIPTION
      "<Definition>A table containing Event History data collected. 
        A request for an object from a row that has not been 
        instantiated or has been cleared shall return a noSuchName 
        error.
       <TableType> dynamic
       <Object Identifier> 1.3.6.1.4.1.1206.4.2.6.4.4
      "
::= { globalReport 4 }

eventLogEntry  OBJECT-TYPE
   SYNTAX  EventLogEntry
   ACCESS  not-accessible
   STATUS  mandatory
   DESCRIPTION
      "<Definition>This object defines an entry in the event log 
        Table. 
<Remark> EventLogTable was modified in NTCIP 1103 v03 to add an entry eventLogTimeMilliseconds Integer, which did not exist in NTCIP 1103 v02.
       <Object Identifier> 1.3.6.1.4.1.1206.4.2.6.4.4.1
      "
INDEX { eventLogClass, eventLogNumber }
::= { eventLogTable 1 }

EventLogEntry ::= SEQUENCE {
   eventLogClass   INTEGER,
   eventLogNumber  INTEGER,
   eventLogID      INTEGER,
   eventLogTime    Counter,
   eventLogValue   Opaque,
eventLogTimeMilliseconds INTEGER }

-- A.7.7.1 Event Log Class Parameter
eventLogClass  OBJECT-TYPE
   SYNTAX  INTEGER (1..255)
   ACCESS  read-only
   STATUS  mandatory
   DESCRIPTION
      "<Definition>This object contains the class of the associated 
        event as defined in the eventLogConfig Table. 
       <Object Identifier> 1.3.6.1.4.1.1206.4.2.6.4.4.1.1
      "
::= { eventLogEntry 1 }

-- A.7.7.2 Event Log Number Parameter
eventLogNumber  OBJECT-TYPE
   SYNTAX  INTEGER (1..255)
   ACCESS  read-only
   STATUS  mandatory
   DESCRIPTION
      "<Definition>The event number within this class for this 
        event. Event numbers shall be assigned starting at 1 and 
        shall increase to the value specified by the associated 
        eventClassLimit for the class associated with the rows. 
        Events shall maintain a chronological ordering in the table 
        with the oldest event of a class occupying the row with 
        eventNumber = 1, and subsequent events filling subsequent 
        rows. This ordering shall be maintained for those rows 
        still remaining when events are cleared. 
       <Object Identifier> 1.3.6.1.4.1.1206.4.2.6.4.4.1.2
      "
::= { eventLogEntry 2 }

-- A.7.7.3 Event Log ID Parameter
eventLogID  OBJECT-TYPE
   SYNTAX  INTEGER (1..65535)
   ACCESS  read-only
   STATUS  mandatory
   DESCRIPTION
      "<Definition>This object contains the event configuration ID 
        (from the eventLogConfigTable) that caused this table entry. 
        It indicates the row in the eventLogConfig table responsible 
        for this event entry. 
       <Object Identifier> 1.3.6.1.4.1.1206.4.2.6.4.4.1.3
      "
::= { eventLogEntry 3 }

-- A.7.7.4 Event Log Time Parameter
eventLogTime  OBJECT-TYPE
   SYNTAX  Counter
   ACCESS  read-only
   STATUS  mandatory
   DESCRIPTION
      "<Definition>The time that the event was detected. If the 
        device supports the globalTime object, the value shall 
        reflect the value of globalTime when the event occurred, 
        otherwise this shall be the time in seconds since the device 
        powered up. The event shall be detected and timestamped 
        within one second from the event becoming true. The event 
        shall be logged in the table within five seconds of the event 
        being detected. These timing resolutions may be modified by a 
        device profile. 
       <Unit>second
       <Object Identifier> 1.3.6.1.4.1.1206.4.2.6.4.4.1.4
       "
::= { eventLogEntry 4 }

-- A.7.7.5 Event Log Value Parameter
eventLogValue  OBJECT-TYPE
   SYNTAX  Opaque
   ACCESS  read-only
   STATUS  mandatory
   DESCRIPTION
      "<Definition>The value of this object is set to the BER 
        encoding of the value referenced by the eventConfigLogOID 
        of the associated eventLogID when the event was logged. Its 
        length is variable. The value shall not contain any padding 
        characters either before or after the values.
        NOTE – Opaque objects are doubly wrapped. For SNMP 
        operations, which use BER, this would be {type, length, 
        {type, length, value}}. For example, a zero-length octet 
        string, would be encoded in BER as 0x44 02 04 00. For STMP 
        or SFMP operations, which use OER, this would be { length, 
        {type, length, value}}. For example, the same example would 
        be encoded in OER as 0x02 04 00. 
       <Object Identifier> 1.3.6.1.4.1.1206.4.2.6.4.4.1.5
      "
::= { eventLogEntry 5 }

-- A.7.7.6 Event Log Time Milliseconds Parameter
eventLogTimeMilliseconds  OBJECT-TYPE
   SYNTAX  INTEGER (0..999)
   ACCESS  read-only
   STATUS  mandatory
   DESCRIPTION
       "<Definition>The number of milliseconds after the beginning of
        the second indicated by the value of eventLogTime at which the 
        event was detected. Devices that do not support sub-second 
        event time resolution shall always set this object to zero. When
        implementing eventLogTimeMilliseconds, devices require a time source
        with millisecond-level resolution, such as GPS or TIA (International
        Atomic Time).
       <Unit>milliseconds
       <Object Identifier> 1.3.6.1.4.1.1206.4.2.6.4.4.1.6
       "
::= { eventLogEntry 6 }

-- A.7.7.7 Total Event Log Counter Parameter
numEvents  OBJECT-TYPE
   SYNTAX  INTEGER (0..65535)
   ACCESS  read-only
   STATUS  mandatory
   DESCRIPTION
      "<Definition> This object is a counter that gets incremented 
        every time an event occurs and shall initialize to zero at 
        power up. The value shall roll over each time it exceeds 
        the maximum of 65535. 
       <Unit>Events
       <Object Identifier> 1.3.6.1.4.1.1206.4.2.6.4.7
      "
::= { globalReport 7 }

-- A.7.7.8 Event Log Time Latency Parameter
eventTimeLatency  OBJECT-TYPE
   SYNTAX  INTEGER (0..1000)
   ACCESS  read-only
   STATUS  mandatory
   DESCRIPTION
      "<Definition> This object indicates the maximum amount of time,
        in milliseconds, that may elapse between an event’s occurrence
        and the time reported for that event entry in the eventLogTable.
        This is a global, constant value that reports the capability
        of the device with respect to event-reporting latency. It should
        account for all sources of latency, including both hardware and
        firmware delays. If eventTimeLatency has a value of L, this means
        that any event in the eventLogTable may actually have occurred
        up to L milliseconds prior to the time reported by the eventLogTime
        and eventLogTimeMilliseconds values associated with the event. A
        value of 0 indicates that the device reports accurate event times
        with millisecond resolution. A value of 1000 indicates that the
        device cannot accurately report sub-second event times.
       <Unit>milliseconds
       <Object Identifier> 1.3.6.1.4.1.1206.4.2.6.4.8
      "
::= { globalReport 8 }

END  -- NTCIP1103v0352-Report
