--3.1	Ramp Meter Control (RMC) MIB Header Information
--***************************************************************************
-- Filename:    1207v0214.MIB
-- Description: This MIB defines the object definitions for ramp meter control
--              (RMC) units
-- Source:      NTCIP 1207 v02
-- MIB Revision History:
-- 2001         NTCIP 1207:2001 approved
-- 04/30/07     Changed filename and updated copyright years
--              Modified header format and wording of copyright and MIB
--              Distribution Notice
--              Incorporated NTCIP 8004 and NTCIP 8005 formats/requirements
--              Addressed User Comments
-- 06/10/2022	Fixed issue the DEFVAL having numbers instead of names for enumerated
--				objects
--
-- Copyright 2014 by the American Association of State Highway and 
-- Transportation Officials (AASHTO), the Institute of Transportation 
-- Engineers (ITE), and the National Electrical Manufacturers Association 
-- NEMA). All intellectual property rights, including, but not limited to, 
-- the rights of reproduction, translation and display are reserved under the 
-- laws of the United States of America, the Universal Copyright 
-- Convention, the Berne Convention, and the International and Pan-
-- American Copyright Conventions. Except as licensed or permitted, you may 
-- not copy these materials without prior written permission from AASHTO, ITE, 
-- or NEMA. Use of these materials does not give you any rights of ownership 
-- or claim of copyright in or to these materials.
--
--                     Joint NEMA, AASHTO, and ITE
--                  NTCIP Management Information Base
--                        DISTRIBUTION NOTICE
--
-- To the extent that these materials are distributed by AASHTO / ITE / NEMA 
-- in the form of a Data Dictionary ("DD") or Management Information Base 
-- ("MIB"), AASHTO / ITE / NEMA extend the following permission:
-- You may make and/or distribute unlimited copies, including derivative 
-- works, of the DD or MIB, including copies for commercial distribution, 
-- provided that:
-- (i)  each copy you make and/or distribute contains the citation "Derived 
-- from NTCIP 0000 [insert the document number]. Used by permission of AASHTO 
-- / ITE / NEMA.";
-- (ii)  the copies or derivative works are not made part of the standards 
-- publications or works offered by other standards developing organizations 
-- or publishers or as works-for-hire not associated with commercial hardware 
-- or software products intended for field implementation;
-- iii)  use of the DD or MIB is restricted in that the syntax fields may be 
-- modified only to reflect a more restrictive subrange or enumerated values;
-- (iv)  the description field may be modified but only to the extent that:
-- (a) only those bit values or enumerated values that are supported are 
-- listed; and (b) the more restrictive subrange is expressed.
--
-- These materials are delivered "AS IS" without any warranties as to their 
-- use or performance.
--
-- AASHTO / ITE / NEMA and their suppliers do not warrant the performance or 
-- results you may obtain by using these materials. AASHTO / ITE / NEMA and 
-- their suppliers make no warranties, express or implied, as to 
-- noninfringement of third party rights, merchantability, or fitness for any 
-- particular purpose. In no event will AASHTO / ITE / NEMA or their 
-- suppliers be liable to you or any third party for any claim or for any 
-- consequential, incidental or special damages, including any lost profits or 
-- lost savings, arising from your reproduction or use of these materials, 
-- even if an AASHTO / ITE / NEMA representative has been advised of the 
-- possibility of such damages.
--
-- Some states or jurisdictions do not allow the exclusion or limitation of 
-- incidental, consequential or special damages, or the exclusion of implied 
-- warranties, so the above limitations may not apply to you.
--
-- Use of these materials does not constitute an endorsement or affiliation by 
-- or between AASHTO, ITE, or NEMA and you, your company, or your products and 
-- services.
--
-- If you are unwilling to accept the foregoing restrictions, you should 
-- immediately return these materials.
--
--NTCIP is a trademark of AASHTO/ITE/NEMA.
--*****************************************************************************

NTCIP1207v0214-MIB   DEFINITIONS ::= BEGIN

IMPORTS
   OBJECT-TYPE --, TIMETICKS
           FROM RFC-1212
   ramp
-- Deleted devices to reference from TMIB-II
-- and added references to ramp
FROM NTCIP8004v02;

--3.2	RMC General Configuration Node
rmcCfg   OBJECT IDENTIFIER::= { ramp 1 }
-- This node is an identifier used to group all objects for the configuration 
-- of general parameters that are common to all ramp meter control units.

--3.2.1	Communication Refresh Threshold Time
rmcCommRefreshThreshold OBJECT-TYPE
SYNTAX   INTEGER (0..65535)
ACCESS   read-write
STATUS   mandatory
DESCRIPTION
"<Definition> This is an RMC parameter that is being used for each metered lane. If no successful SET command communication has been issued to the rmcCommActionMode-object of a metered lane for the time indicated in this threshold, the value of the  rmcCommActionStatus-object for that metered lane shall be set to 'noComm'. This value shall be expressed in 1-second increments. A suggested usable range is 0, 20 to 14400. A value of zero (0) shall inhibit communications refresh timing.
<Unit> second
<Object Identifier> 1.3.6.1.4.1.1206.4.2.2.1.1"
REFERENCE
"see Clause A.3"
DEFVAL   { 0 }
::={ rmcCfg 1 }

--3.2.2	Calculation Interval
rmcCalcInterval  OBJECT-TYPE
SYNTAX   INTEGER (1..255)
ACCESS   read-write
STATUS   mandatory
DESCRIPTION 
"Indicates the duration of a single calculation interval consisting of data analysis, averaging and processing. This value shall be expressed in 1-second increments. A suggested usable range is 10 to 30.
<Unit> second
<Object Identifier> 1.3.6.1.4.1.1206.4.2.2.1.2"
REFERENCE
"See Clause A.2.1, A.2.2, A.2.2.1, A.2.2.2, A.2.2.3, A.2.3.1, A.3, A.4.1, 
A.7.1, A.7.2, A.8.3.1.4.2, A.8.5.3.4.2, and A.9.1"
DEFVAL   { 30 }
::={ rmcCfg 2 }

--3.3	Mainline Lane Configuration, Control And Status Node
rmcML  OBJECT IDENTIFIER ::={ ramp 2 }

-- This node is an identifier used to group all objects for the configuration, 
-- control and status of the mainline lanes that are common to all ramp meter 
-- control units.

--3.3.1	Averaging Periods 
rmcAveragingPeriods   OBJECT-TYPE
SYNTAX   INTEGER (1..255)
ACCESS   read-write
STATUS   mandatory
DESCRIPTION
"This value indicates the number of calculation intervals over which the mainline station averages are be calculated. This value shall be expressed in 1-interval increments. A suggested usable range is 1 to 60.
<Unit> interval
<Object Identifier> 1.3.6.1.4.1.1206.4.2.2.2.1"
REFERENCE
"See Clause A.4"
DEFVAL   { 2 }
::={ rmcML 1 }

--3.3.2	Maximum Number of Mainline Lanes
rmcMaxNumML   OBJECT-TYPE
SYNTAX   INTEGER (1..255)
ACCESS   read-only
STATUS   mandatory
DESCRIPTION 
"Indicates the maximum number of mainline lanes that can be stored in the Mainline Lane Configuration and Control Table, and, by association, in all other mainline lane tables.
<Unit> number
<Object Identifier> 1.3.6.1.4.1.1206.4.2.2.2.2"
REFERENCE
"See Clause A.2.1"
::={ rmcML 2 }
-- USERS TAKE NOTE OF MULTIPLE VERSIONS -
-- the INTEGER range was changed to start at 1 instead of 0. This 
-- does not cause backwards compatibility problems because this object would 
-- not have been supported, if the function was not supported in the device.

--3.3.3	Number of Mainline Lanes
rmcNumML   OBJECT-TYPE
SYNTAX   INTEGER (1..255)
ACCESS   read-only
STATUS   mandatory
DESCRIPTION 
"Indicates the actual number of mainline lanes that are present in the Mainline Lane Configuration and Control Table, and, by association, in all other mainline lane tables. This value shall not exceed the value of the rmcMaxNumML-object.
<Unit> number
<Object Identifier> 1.3.6.1.4.1.1206.4.2.2.2.3"
REFERENCE
"See Clause A.2.1"
::={ rmcML 3 }
-- USERS TAKE NOTE OF MULTIPLE VERSIONS -
-- the INTEGER range was changed to start at 1 instead of 0. This 
-- does not cause backwards compatibility problems because this object would 
-- not have been supported, if the function was not supported in the device.

--3.3.4	Mainline Lane Configuration and Control Table
rmcMLCtrlTable OBJECT-TYPE
SYNTAX   SEQUENCE OF RmcMLCtrlEntry
ACCESS   not-accessible
STATUS   mandatory
DESCRIPTION 
"A table containing the configuration and control information for the mainline lanes.
<Table Type> static
<Object Identifier> 1.3.6.1.4.1.1206.4.2.2.2.4"
::={ rmcML 4 }

rmcMLCtrlEntry OBJECT-TYPE
SYNTAX   RmcMLCtrlEntry
ACCESS   not-accessible
STATUS   mandatory
DESCRIPTION 
"Configuration and control parameters of the mainline lane table. A particular row of this table can be managed using the rmcMLMode-object.
<Object Identifier> 1.3.6.1.4.1.1206.4.2.2.2.4.1"
INDEX { rmcMLNumber }
::={ rmcMLCtrlTable 1 }

RmcMLCtrlEntry ::=SEQUENCE { 
	rmcMLNumber                   INTEGER,
	rmcMLMode                     INTEGER,
	rmcMLLeadZoneLength           INTEGER, -- deprecated
	rmcMLTrailZoneLength          INTEGER, -- deprecated
	rmcMLUsageMode                INTEGER,
	rmcMLSpeedTrapSpacing         INTEGER, -- deprecated
	rmcMLErraticCount             INTEGER,
	rmcMLMaxPresence              INTEGER,
	rmcMLNoActivity               INTEGER,
	rmcVehicleLength              INTEGER, -- deprecated
	rmcMLLeadZoneLengthV2         INTEGER,
	rmcMLTrailZoneLengthV2        INTEGER,
	rmcMLSpeedTrapSpacingV2       INTEGER,
	rmcVehicleLengthV2            INTEGER }

--3.3.4.1	Mainline Lane Number
rmcMLNumber   OBJECT-TYPE
SYNTAX   INTEGER (1..255)
ACCESS   read-only
STATUS   mandatory
DESCRIPTION
"Enumerated listing of the mainline lanes. 
This value shall not exceed the value of the rmcMaxNumML-object.
<Unit> number
<Object Identifier> 1.3.6.1.4.1.1206.4.2.2.2.4.1.1"
REFERENCE
"See Clause A.2.1"
::={ rmcMLCtrlEntry 1 }
-- USERS TAKE NOTE OF MULTIPLE VERSIONS -
-- the INTEGER range was changed to start at 1 instead of 0. This 
-- does not cause backwards compatibility problems because this object would 
-- not have been supported, if the function was not supported in the device.

--3.3.4.2	Mainline Lane Mode
rmcMLMode   OBJECT-TYPE
SYNTAX   INTEGER { 
   disabled (1),
   singleEnabledLead (2),
   singleEnabledTrail (3),
   dualEnabled (4),
   preprocessedEnabled (5) }
ACCESS   read-write
STATUS   mandatory
DESCRIPTION
"Indicates the mode of the mainline lane. The values are:
disabled - indicates that no detector is enabled. When set to this value, the content of the entire row shall be invalidated; however, the row shall not be deleted.
singleEnabledLead - indicates that only the leading detector shall be enabled. The trailing detector status shall be disabled.
singleEnabledTrail - indicates that only the trailing detector shall be enabled. The leading detector status shall be disabled.
dualEnabled - indicates that both the leading and trailing detectors shall be enabled.
preprocessedEnabled - indicates that no detector shall be enabled but traffic data is provided by another process / device.
<Object Identifier> 1.3.6.1.4.1.1206.4.2.2.2.4.1.2"
REFERENCE
"See Clause A.2.1"
DEFVAL   { singleEnabledLead }
::={ rmcMLCtrlEntry 2 }

--3.3.4.3	Leading Detection Zone Length
rmcMLLeadZoneLength  OBJECT-TYPE
SYNTAX   INTEGER (0..255)
ACCESS   read-write
STATUS   deprecated
DESCRIPTION
"Indicates the detection zone length of the leading detector. 
This value shall be expressed in 0.1-meter increments (i.e, 40 = 4.0 meters). 
A suggested usable range is 0 to 50.
<Unit> tenth of meter
<Object Identifier> 1.3.6.1.4.1.1206.4.2.2.2.4.1.3"
REFERENCE
"See Clause A.2.1"
DEFVAL   { 30 }
::={ rmcMLCtrlEntry 3 }
-- USERS TAKE NOTE OF MULTIPLE VERSIONS - this object was deprecated in 
-- version 02 and replaced with an object of a similar name and function. 
-- The reason for the development of the new object and deprecation of this 
-- object is that deployment experiences have shown that the unit resolution 
-- was not fine enough for applications. This new object uses 0.01-meter 
-- increments instead of the 0.1-meter increments used in this object.

--3.3.4.4	Trailing Detection Zone Length
rmcMLTrailZoneLength  OBJECT-TYPE
SYNTAX   INTEGER (0..255)
ACCESS   read-write
STATUS   deprecated
DESCRIPTION
"Indicates the detection zone length of the trailing detector. This value shall be expressed in 0.1-meter increments (i.e, 40 = 4.0 meters). A suggested usable range is 0 to 50.
<Unit> tenth of meter
<Object Identifier> 1.3.6.1.4.1.1206.4.2.2.2.4.1.4"
REFERENCE
"See Clause A.2.1"
DEFVAL   { 30 }
::={ rmcMLCtrlEntry 4 }
-- USERS TAKE NOTE OF MULTIPLE VERSIONS - this object was deprecated in 
-- version 02 and replaced with an object of a similar name and function. 
-- The reason for the development of the new object and deprecation of this 
-- object is that deployment experiences have shown that the unit resolution 
-- was not fine enough for applications. This new object uses 0.01-meter 
-- increments instead of the 0.1-meter increments used in this object.

--3.3.4.5	Lane Usage Mode
rmcMLUsageMode  OBJECT-TYPE
SYNTAX   INTEGER { 
   notUsed (1),
   schemeF (2),
   schemeO (3),
   schemeFO (4),
   schemeS (5),
   schemeFS (6),
   schemeOS (7),
   schemeFOS (8),
   determinedByOther (9) }
ACCESS   read-write
STATUS   mandatory
DESCRIPTION
"Indicates which mainline station traffic parameters will use the data from 
this lane. The values are: 
notUsed - the lane data will not be used to calculate any mainline station 
    parameter.
schemeF - the lane data will be used to calculate the rmcAverageFlowRate-object
schemeO - the lane data will be used to calculate the rmcAverageOccupancy-object
schemeFO - the lane data will be used to calculate the rmcAverageFlowRate-object and rmcAverageOccupancy-object
schemeS - the lane data will be used to calculate the rmcAverageSpeed-object
schemeFS - the lane data will be used to calculate the rmcAverageFlowRate-object and rmcAverageSpeed-object
schemeOS - the lane data will be used to calculate the rmcAverageOccupancy-object and rmcAverageSpeed-object 
schemeFOS - the lane data will be used to calculate the rmcAverageFlowRate-object, rmcAverageOccupancy-object and rmcAverageSpeed-object
determinedByOther - the rmcMLUsageStatus-object will determine the mainline lane data usage. 
<Object Identifier> 1.3.6.1.4.1.1206.4.2.2.2.4.1.5"
REFERENCE
"See Clause A.2.1"
DEFVAL   { schemeFO }
::={ rmcMLCtrlEntry 5 }

--3.3.4.6	Speed Trap Spacing
rmcMLSpeedTrapSpacing  OBJECT-TYPE
SYNTAX   INTEGER (0..255)
ACCESS   read-write
STATUS   deprecated
DESCRIPTION
"Indicates the spacing between the leading and trailing detector measured from upstream edge to upstream edge of the detectors. This value shall be expressed in 0.1-meter increments (i.e, 40 = 4.0 meters). 
A suggested usable range is 20 to 150. 
A value of zero (0) shall inhibit the calculation of speed.
<Unit> tenth of meter
<Object Identifier> 1.3.6.1.4.1.1206.4.2.2.2.4.1.6"
REFERENCE
"See Clause A.2.1"
DEFVAL   { 61 }
::={ rmcMLCtrlEntry 6 }
-- USERS TAKE NOTE OF MULTIPLE VERSIONS - this object was deprecated in 
-- version 02 and replaced with an object of a similar name and function. 
-- The reason for the development of the new object and deprecation of this 
-- object is that deployment experiences have shown that the unit resolution 
-- was not fine enough for applications. This new object uses 0.01-meter 
-- increments instead of the 0.1-meter increments used in this object.

--3.3.4.7	Mainline Erratic Count Threshold
rmcMLErraticCount   OBJECT-TYPE
SYNTAX   INTEGER (0..255)
ACCESS   read-write
STATUS   mandatory
DESCRIPTION 
"If the vehicle count, over the most recently completed calculation interval,on a mainline lane detector exceeds this threshold, the rmcMLLeadStatus- (or 
rmcMLTrailStatus-) object for that detector shall be set to a value of 
'erraticCount'. 
This value shall be expressed in 1-vehicle increments. 
A suggested usable range is 0 to 30. 
A value of zero (0) shall inhibit the erratic count testing.
<Unit> number
<Object Identifier> 1.3.6.1.4.1.1206.4.2.2.2.4.1.7"
REFERENCE
"See Clause A.2.1"
DEFVAL   { 30 }
::={ rmcMLCtrlEntry 7 } 

--3.3.4.8	Mainline Maximum Presence Threshold
rmcMLMaxPresence   OBJECT-TYPE
SYNTAX   INTEGER (0..65535)
ACCESS   read-write
STATUS   mandatory
DESCRIPTION 
"If the input of a mainline lane detector has been continuously actuated for longer than this threshold, the rmcMLLeadStatus- (or rmcMLTrailStatus-) object for that detector shall be set to a value of 'maxPresence'. 
This value shall be expressed in 1-minute increments. 
A suggested usable range is 0 to 1500. 
A value of zero (0) shall inhibit the maximum presence testing. 
<Unit> minute
<Object Identifier> 1.3.6.1.4.1.1206.4.2.2.2.4.1.8"
REFERENCE
"See Clause A.2.1"
DEFVAL   { 2 }
::={ rmcMLCtrlEntry 8 }

--3.3.4.9	Mainline No Activity Threshold
rmcMLNoActivity   OBJECT-TYPE
SYNTAX   INTEGER (0..65535)
ACCESS   read-write
STATUS   mandatory
DESCRIPTION 
"If the input of a mainline lane detector has not been actuated for longer than this threshold, the rmcMLLeadStatus- (or  rmcMLTrailStatus-) object for that detector shall be set to a value of 'noActivity'. 
This value shall be expressed in 1-minute increments. 
A suggested usable range is 0 to 1500. 
A value of zero (0) shall inhibit the no activity testing.
<Unit> minute
<Object Identifier> 1.3.6.1.4.1.1206.4.2.2.2.4.1.9"
REFERENCE
"See Clause A.2.1"
DEFVAL   { 0 }
::={ rmcMLCtrlEntry 9 }

--3.3.4.10	Typical Vehicle Length
rmcVehicleLength   OBJECT-TYPE
SYNTAX   INTEGER (0..255)
ACCESS   read-write
STATUS   deprecated
DESCRIPTION 
"Indicates the length of a typical vehicle in 0.1 m, which is used for mainline lane speed estimation with a single working detector per mainline lane. 
This value shall be expressed in 0.1-meter increments (i.e, 40 = 4.0 meters). 
A suggested usable range is 0 and 15 to 100. 
A value of zero (0) shall inhibit speed estimation.
<Unit> tenth of meter
<Object Identifier> 1.3.6.1.4.1.1206.4.2.2.2.4.1.10"
REFERENCE
"See Clause A.2.1"
DEFVAL   { 0 }
::={ rmcMLCtrlEntry 10 }
-- USERS TAKE NOTE OF MULTIPLE VERSIONS - this object was deprecated in 
-- version 02 and replaced with an object of a similar name and function. 
-- The reason for the development of the new object and deprecation of this 
-- object is that deployment experiences have shown that the unit resolution 
-- was not fine enough for applications. This new object uses 0.01-meter 
-- increments instead of the 0.1-meter increments used in this object.

--3.3.4.11	Leading Detection Zone Length - Version 2
rmcMLLeadZoneLengthV2  OBJECT-TYPE
SYNTAX   INTEGER (0..65535)
ACCESS   read-write
STATUS   mandatory
DESCRIPTION
"Indicates the detection zone length of the leading detector. 
This value shall be expressed in 0.01-meter increments (i.e, 400 = 4.00 meters). 
A suggested usable range is 000 to 500.
<Unit> hundredth of meter
<Object Identifier> 1.3.6.1.4.1.1206.4.2.2.2.4.1.11"
REFERENCE
"See Clause A.2.1"
DEFVAL   { 300 }
::={ rmcMLCtrlEntry 11 }
-- USERS TAKE NOTE OF MULTIPLE VERSIONS - this object replaces the version 1
-- object of the same name and function. However, deployment experiences 
-- have shown that the unit is not fine enough for applications. This new 
-- object uses 0.01-meter increments instead of the 0.1-meter increments 
-- used in version 1. Because of this, the SYNTAX range also needed to 
-- change.

--3.3.4.12	Trailing Detection Zone Length - Version 2
rmcMLTrailZoneLengthV2  OBJECT-TYPE
SYNTAX   INTEGER (0..65535)
ACCESS   read-write
STATUS   mandatory
DESCRIPTION
"Indicates the detection zone length of the trailing detector. 
This value shall be expressed in 0.01-meter increments (i.e, 400 = 4.00 meters). 
A suggested usable range is 000 to 500.
<Unit> hundredth of meter
<Object Identifier> 1.3.6.1.4.1.1206.4.2.2.2.4.1.12"
REFERENCE
"See Clause A.2.1"
DEFVAL   { 300 }
::={ rmcMLCtrlEntry 12 }
-- USERS TAKE NOTE OF MULTIPLE VERSIONS - this object replaces the version 1
-- object of the same name and function. However, deployment experiences 
-- have shown that the unit is not fine enough for applications. This new 
-- object uses 0.01-meter increments instead of the 0.1-meter increments 
-- used in version 1. Because of this, the SYNTAX range also needed to 
-- change.

--3.3.4.13	Speed Trap Spacing - Version 2
rmcMLSpeedTrapSpacingV2  OBJECT-TYPE
SYNTAX   INTEGER (0..65535)
ACCESS   read-write
STATUS   mandatory
DESCRIPTION
"Indicates the spacing between the leading and trailing detector measured from upstream edge to upstream edge of the detectors. 
This value shall be expressed in 0.01-meter increments (i.e, 400 = 4.00 meters). 
A suggested usable range is 200 to 1500. 
A value of zero (0) shall inhibit the calculation of speed.
<Unit> hundredth of meter
<Object Identifier> 1.3.6.1.4.1.1206.4.2.2.2.4.1.13"
REFERENCE
"See Clause A.2.1"
DEFVAL   { 61 }
::={ rmcMLCtrlEntry 13 }
-- USERS TAKE NOTE OF MULTIPLE VERSIONS - this object replaces the version 1
-- object of the same name and function. However, deployment experiences 
-- have shown that the unit is not fine enough for applications. This new 
-- object uses 0.01-meter increments instead of the 0.1-meter increments 
-- used in version 1. Because of this, the SYNTAX range also needed to 
-- change.

--3.3.4.14	Typical Vehicle Length - Version 2
rmcVehicleLengthV2   OBJECT-TYPE
SYNTAX   INTEGER (0..65535)
ACCESS   read-write
STATUS   mandatory
DESCRIPTION 
"Indicates the length of a typical vehicle in 0.01 m, which is used for mainline lane speed estimation with a single working detector per mainline lane. 
This value shall be expressed in 0.1-meter increments (i.e, 400 = 4.00 meters). 
A suggested usable range is 0 and 150 to 1000. 
A value of zero (0) shall inhibit speed estimation.
<Unit> hundredth of meter
<Object Identifier> 1.3.6.1.4.1.1206.4.2.2.2.4.1.14"
REFERENCE
"See Clause A.2.1"
DEFVAL   { 0 }
::={ rmcMLCtrlEntry 14 }
-- USERS TAKE NOTE OF MULTIPLE VERSIONS - this object replaces the version 1
-- object of the same name and function. However, deployment experiences 
-- have shown that the unit is not fine enough for applications. This new 
-- object uses 0.01-meter increments instead of the 0.1-meter increments 
-- used in version 1. Because of this, the SYNTAX range also needed to 
-- change.

--3.3.5	Maximum Number of Mainline Flow-based No Activity Entries
rmcMaxNumFlowNoActivityTableEntries   OBJECT-TYPE
SYNTAX   INTEGER (1..255)
ACCESS   read-only
STATUS   mandatory
DESCRIPTION 
"Indicates the maximum number of entries in the Mainline Flow-based No Activity Table. 
A suggested minimum value is two (2).
<Unit> number
<Object Identifier> 1.3.6.1.4.1.1206.4.2.2.2.9"
REFERENCE
"See Clause A.4.2"
::={ rmcML 9 }

--3.3.6	Number of Mainline Flow-based No Activity Entries
rmcNumFlowNoActivityTableEntries   OBJECT-TYPE
SYNTAX   INTEGER (1..255)
ACCESS   read-only
STATUS   mandatory
DESCRIPTION 
"Indicates the actual number of entries in the Mainline Flow-based No Activity Table. This value shall not exceed the value of the rmcMaxNumFlowNoActivityTableEntries-object.
<Unit> number
<Object Identifier> 1.3.6.1.4.1.1206.4.2.2.2.10"
REFERENCE
"See Clause A.4.2"
::={ rmcML 10 }

--3.3.7	Mainline Flow-based No Activity Table 
rmcMLFlowBasedNoActivityTable   OBJECT-TYPE
SYNTAX   SEQUENCE OF RmcMLFlowBasedNoActivityEntry
ACCESS   not-accessible
STATUS   mandatory
DESCRIPTION 
"A table containing the configuration information for an entry in the Mainline Flow-based No Activity Table. The purpose of this table is to define the duration for the flow-based no activity diagnostic test. The duration will vary with the Average Station Flow Rate.

Flow-based No Activity Threshold value in the first entry shall be the maximum threshold. 
If the value of the rmcAverageFlowRate-object is less than the value of the rmcFlowRateNoActivityThreshold-object in this entry row and greater than the value in the following entry, then the Flow-based No Activity Duration in that entry shall be used. 
If the value of the rmcAverageFlowRate-object is less than the value of the rmcFlowRateNoActivityThreshold-object in the last entry, then the Flow-based No Activity Duration of the last entry shall be used. 
If the value of the rmcAverageFlowRate-object is greater than the maximum value of the rmcFlowRateNoActivityThreshold-object in the table, then the Mainline Flow-based No Activity test shall be disabled. 

The first instance of the rmcFlowRateNoActivityThreshold-object whose value is zero indicates the end of the valid table contents. Rows prior to the end of the valid rows that contain a value of zero (0) for the rmcFlowBasedNoActivityDuration-object indicate that this row shall NOT be used for flow-based no activity testing.

Additionally, the following rules shall be used when configuring this table:
- All rmcFlowRateNoActivityThreshold-object entries in the table shall be 
  decreasing for increasing indices.
- All rmcFlowBasedNoActivityDuration-object entries in the table shall be 
  non-decreasing for increasing indices. 
- if the value of the rmcNumFlowRateLanes-object is '0', then the 
  rmcFlowRateNoActivityDuration-object shall have a value of '0'. 

<Table Type> static. 
<Object Identifier> 1.3.6.1.4.1.1206.4.2.2.2.11"
::={ rmcML 11 }

rmcMLFlowBasedNoActivityEntry   OBJECT-TYPE
SYNTAX   RmcMLFlowBasedNoActivityEntry
ACCESS   not-accessible
STATUS   mandatory
DESCRIPTION 
"Configuration parameters for a row of the table. A particular entry/row of this table can be managed using the rmcFlowBasedNoActivityDuration-object. 
When this object is set to zero, then the associated row shall be ignored for the determination of the duration value for the flow-based no activity diagnostic test.
<Object Identifier> 1.3.6.1.4.1.1206.4.2.2.2.11.1"
INDEX { rmcMLFlowBasedNoActivityIndex }
::={ rmcMLFlowBasedNoActivityTable 1 }

RmcMLFlowBasedNoActivityEntry ::=SEQUENCE {
   rmcMLFlowBasedNoActivityIndex   INTEGER,
   rmcFlowBasedNoActivityThreshold   INTEGER,
   rmcFlowBasedNoActivityInterval   INTEGER }

--3.3.7.1	Mainline Flow-based No Activity Index Parameter
rmcMLFlowBasedNoActivityIndex   OBJECT-TYPE
SYNTAX   INTEGER (1..255)
ACCESS   read-only
STATUS   mandatory
DESCRIPTION
"Key into this table defining an enumerated listing of row entries that indicate the number of flow-based no activity threshold / 
duration pairs stored for this RMC unit. 
This value shall not exceed the value of the rmcMaxNumFlowNoActivityTableEntries-object.
<Unit> number
<Object Identifier> 1.3.6.1.4.1.1206.4.2.2.2.11.1.1"
REFERENCE
"See Clause A.4.2"
::={ rmcMLFlowBasedNoActivityEntry 1 }

--3.3.7.2	Mainline Flow-Based No Activity Threshold Parameter
rmcFlowBasedNoActivityThreshold   OBJECT-TYPE
SYNTAX   INTEGER (0..65535)
ACCESS   read-write
STATUS   mandatory
DESCRIPTION
"Indicates the flow-based no activity threshold which will be used to determine the no activity duration value. 
This value shall be expressed in 1-vph increments. 
A suggested usable range is 0, 200-3600. 
The first instance of a value of zero (0) indicates that this is the last valid entry of the table. Additional rows of the table, regardless of the value, shall be ignored.
<Unit> vehicles per hour
<Object Identifier> 1.3.6.1.4.1.1206.4.2.2.2.11.1.2"
REFERENCE
"See Clause A.4.2"
::={ rmcMLFlowBasedNoActivityEntry 2 }

--3.3.7.3	Mainline Flow-based No Activity Interval Parameter
rmcFlowBasedNoActivityInterval  OBJECT-TYPE
SYNTAX   INTEGER (0..65535)
ACCESS   read-write
STATUS   mandatory
DESCRIPTION
"Indicates the duration of the flow-based no activity interval, which is associated with the flow-based no activity threshold defined in the same row.
This value shall be expressed in 1-minute increments. 
A suggested usable range is 0, 1-240 minutes.
<Unit> minute
<Object Identifier> 1.3.6.1.4.1.1206.4.2.2.2.11.1.3"
REFERENCE
"See Clause A.4.2"
::={ rmcMLFlowBasedNoActivityEntry 3 }

--3.3.8	Average Mainline Station Flow Rate
rmcAverageFlowRate   OBJECT-TYPE
SYNTAX   INTEGER (0..65535)
ACCESS   read-only
STATUS   mandatory
DESCRIPTION
"Indicates the flow rate measured over the rmcAveragingPeriods-object number of preceding calculation intervals. The flow rate shall be determined by calculating the average of all mainline lanes whose rmcMLStatus-object value is NOT 'total failure' or 'disabled' at any time during the previous averaging periods number of calculation intervals, AND whose rmcMLUsageStatus-object has a value of 'schemeF', 'schemeFO', 'schemeFS', or 'schemeFOS'. Any mainline lane whose rmcMLStatus-object had a value of 'totalFailure' during 
the Averaging Periods shall not be used for the calculation. 
The value of this object shall be calculated using a lane average. 
The value shall be expressed in vph in 1-vph increments.
<Unit> vehicles per hour
<Object Identifier> 1.3.6.1.4.1.1206.4.2.2.2.5"
REFERENCE
"See Clause A.4"
::={ rmcML 5 }

--3.3.9	Average Mainline Station Occupancy
rmcAverageOccupancy   OBJECT-TYPE
SYNTAX   INTEGER (0..65535)
ACCESS   read-only
STATUS   mandatory
DESCRIPTION
"Indicates the occupancy measured over the rmcAveragingPeriods-object number of preceding calculation intervals. The occupancy shall be determined by calculating the average of all mainline lanes whose rmcMLStatus-object value is NOT 'total failure' or 'disabled' at any time during the previous averaging periods number of calculation intervals, AND whose rmcMLUsageStatus-object has a value of 'schemeO', 'schemeFO', 'schemeOS', or 'schemeFOS'. Any mainline lane whose rmcMLStatus-object had a value of 'totalFailure' during the Averaging Periods shall not be used for the calculation.
The value of this object shall be calculated using a lane average.
The value shall be expressed in 0.1-percent increments (i.e, 40 = 4.0 percent).
<Unit> tenth of percent
<Object Identifier> 1.3.6.1.4.1.1206.4.2.2.2.6"
REFERENCE
"See Clause A.4"
::={ rmcML 6 }

--3.3.10	Average Mainline Station Speed
rmcAverageSpeed  OBJECT-TYPE
SYNTAX   INTEGER (0..255)
ACCESS   read-only
STATUS   mandatory
DESCRIPTION
"Indicates the speed measured over the rmcAveragingPeriods-object number of preceding calculation intervals. The speed shall be determined by calculating the average of all mainline lanes using (A or B) and C:
A) those mainline lanes whose rmcMLStatus-object value is NOT 'total failure' or 'disabled' at any time during the previous averaging periods number     of calculation intervals,
OR 
B) those mainline lanes whose rmcMLStatus-object value is 'partial failure' and whose rmcVehicleLength is NOT '0', 
AND 
C) whose rmcMLUsageStatus-object as a value of 'schemeS', 'schemeFS', 'schemeOS', or 'schemeFOS'. 

Any mainline lane whose rmcMLStatus-object had:
- a value of 'totalFailure' during the Averaging Periods, 
OR 
- a value of 'partialFailure' during the Averaging Periods and whose rmcMLMode-object has a value of 'singleEnabledLead' or 'singleEnabledTrail' (only one detector is used and speed estimation is disabled), hall not be used for the calculation. 
The value of this object shall be calculated using a vehicle average. 
The value shall be expressed in 1-km/h increments.
<Unit> kilometers per hour
<Object Identifier> 1.3.6.1.4.1.1206.4.2.2.2.7"
REFERENCE
"See Clause A.4"
::={ rmcML 7 }

--3.3.11	Number of Flow Rate Lanes
rmcNumFlowRateLanes   OBJECT-TYPE
SYNTAX   INTEGER (0..255)
ACCESS   read-only
STATUS   mandatory
DESCRIPTION
"Indicates the number of mainline lanes used to calculate the rmcAverageFlowRate-object during the last calculation interval. 
This value shall not exceed the value of the rmcNumML-object.
<Unit> number
<Object Identifier> 1.3.6.1.4.1.1206.4.2.2.2.12"
REFERENCE
"See Clause A.4"
::={ rmcML 12 }

--3.3.12	Number of Occupancy Lanes
rmcNumAverageOccupancyLanes   OBJECT-TYPE
SYNTAX   INTEGER (0..255)
ACCESS   read-only
STATUS   mandatory
DESCRIPTION
"Indicates the number of mainline lanes used to calculate the rmcAverageOccupancy-object during the last calculation interval. 
This value shall not exceed the value of the rmcNumML-object.
<Unit> number
<Object Identifier> 1.3.6.1.4.1.1206.4.2.2.2.13"
REFERENCE
"See Clause A.4"
::={ rmcML 13 }

--3.3.13	Number of Average Speed Lanes
rmcNumAverageSpeedLanes  OBJECT-TYPE
SYNTAX   INTEGER (0..255)
ACCESS   read-only
STATUS   mandatory
DESCRIPTION
"Indicates the number of mainline lanes used to calculate the rmcAverageSpeed-object during the last calculation interval. 
This value shall not exceed the value of the rmcNumML-object. 
<Unit> number
<Object Identifier> 1.3.6.1.4.1.1206.4.2.2.2.14"
REFERENCE
"See Clause A.4"
::={ rmcML 14 }

--3.3.14	Mainline Lane Status Table
rmcMLStatTable OBJECT-TYPE
SYNTAX   SEQUENCE OF RmcMLStatEntry
ACCESS   not-accessible
STATUS   mandatory
DESCRIPTION 
"A table containing the status information for a mainline lane. 
<Table Type> static
<Object Identifier> 1.3.6.1.4.1.1206.4.2.2.2.8"
::={ rmcML 8 }

rmcMLStatEntry OBJECT-TYPE
SYNTAX   RmcMLStatEntry
ACCESS   not-accessible
STATUS   mandatory
DESCRIPTION 
"Status parameters of the mainline lane status table. This table is directly correlated to the Mainline Lane Configuration and Control Table, which means that the number of rows in this table is exactly the same as the number of rows in the Mainline Lane Configuration and Control Table (AUGMENT TABLE in SNMPv2terminology). Table management can only take place through the Mainline Lane Configuration and Control Table, while this table provides only status information about the mainline lanes.
<Object Identifier> 1.3.6.1.4.1.1206.4.2.2.2.8.1"
INDEX { rmcMLNumber }
::={ rmcMLStatTable 1 }

RmcMLStatEntry ::=SEQUENCE { 
	rmcMLLeadStatus       INTEGER,
	rmcMLTrailStatus      INTEGER,
	rmcMLStatus           INTEGER,
	rmcMLUsageStatus      INTEGER,
	rmcMLHistLeadStatus   INTEGER, -- added in version 2
	rmcMLHistTrailStatus  INTEGER  -- added in version 2
	}

--3.3.14.1	Leading Detector Status
rmcMLLeadStatus  OBJECT-TYPE
SYNTAX   INTEGER { 
   disabled (1),
   working (2),
   otherError (3),
   erraticCount (4),
   maxPresence (5),
   noActivity (6),
   errorAtSensor (7),
   flowBasedNoActivity (8) -- added in version 2
   }
ACCESS   read-only
STATUS   mandatory
DESCRIPTION
"Indicates  the status of the leading  detector. The values are:
disabled - indicates that this detector is not used.
working - indicates that this detector has no error.
otherError - indicates an error not defined here. See Operator's Manual.
erraticCount - indicates that the vehicle count for this detector has exceeded the value of its rmcMLErraticCount-object.
maxPresence - indicates a continuous actuation for this detector that has exceeded the value of its rmcMLMaxPresence-object.
noActivity - indicates a continuous non-actuation for this detector that has exceeded the value of its rmcMLNoActivity-object. 
errorAtSensor - indicates that the sensor for this detector has reported an error. See Operator's manual
flowBasedNoActivity - indicates a continuous non-actuation for this detector that has exceeded the value of its rmcMLFlowBasedNoActivity-object. 
<Object Identifier> 1.3.6.1.4.1.1206.4.2.2.2.8.1.1"
REFERENCE
"See Clause A.2.1"
::={ rmcMLStatEntry 1 }

--3.3.14.2	Trailing Detector Status
rmcMLTrailStatus  OBJECT-TYPE
SYNTAX   INTEGER { 
   disabled (1),
   working (2),
   otherError (3),
   erraticCount (4),
   maxPresence (5),
   noActivity (6),
   errorAtSensor (7),
   flowBasedNoActivity (8) --  added in version 2
   }
ACCESS   read-only
STATUS   mandatory
DESCRIPTION
"Indicates the status of the trailing detector. The values are:
disabled - indicates that this detector is not used.
working - indicates that this detector has no error.
otherError - indicates an error not defined here. See Operator's manual.
erraticCount - indicates that the vehicle count for this detector has exceeded the value of its rmcMLErraticCount-object.
maxPresence - indicates a continuous actuation for this detector that has exceeded the value of its rmcMLMaxPresence-object.
noActivity - indicates a continuous non-actuation for this detector that has exceeded the value of its rmcMLNoActivity-object.
errorAtSensor - indicates that the sensor for this detector has reported an error. See Operator's manual.
flowBasedNoActivity - indicates a continuous non-actuation for this detector that has exceeded the value of its rmcMLFlowBasedNoActivity-object. 
<Object Identifier> 1.3.6.1.4.1.1206.4.2.2.2.8.1.2"
REFERENCE
"See Clause A.2.1"
::={ rmcMLStatEntry 2 }

--3.3.14.3	Lane Status
rmcMLStatus   OBJECT-TYPE
SYNTAX   INTEGER { 
   working (1),
   disabled (2),
   partialFailure (3),
   totalFailure (4) }
ACCESS   read-only
STATUS   mandatory
DESCRIPTION
"Indicates  the status of the mainline lane. The values are:
working - indicates that the rmcMLMode-object has a value of either:
      a.) 'dualEnabled', and both the rmcMLLeadStatus-object and the rmcMLTrailStatus-object have the value of 'working', or
      b.) 'singleEnabledLead', and the rmcMLLeadStatus-object has the value of 'working', or
      c.) 'singleEnabledTrail', and the rmcMLTrailStatus-object has the value of 'working', or
      d.) 'preprocessedEnabled', and the device providing the traffic data has reported no error.
disabled - indicates that the rmcMLMode-object has a value of either:
      a.) 'disabled', or
      b.) 'singleEnabledLead', and the rmcMLLeadStatus-object has the value of 'disabled', or
      c.) 'singleEnabledTrail', and the rmcMLTrailStatus-object has the value of 'disabled'.
partialFailure - indicates that the rmcMLMode-object has a value of 
         'dualEnabled', but the value of one of rmcMLLeadStatus-object and rmcMLTrailStatus-object is NOT 'working', while the value of the other is 'working'.
totalFailure - indicates that the rmcMLMode-object has a value of either:
      a.) 'dualEnabled', but the rmcMLLeadStatus-object and the rmcMLTrailStatus-object both have the value of NOT 'working', or
      b.) 'singleEnabledLead', and the rmcMLLeadStatus-object has the value of 'error', or
      c.) 'singleEnabledTrail', and the rmcMLTrailStatus-object has the value of 'error', or
      d.) 'preprocessedEnabled', and the device providing the traffic data has reported an error.
<Object Identifier> 1.3.6.1.4.1.1206.4.2.2.2.8.1.3"
REFERENCE
"See Clause A.2.1"
::={ rmcMLStatEntry 3 }

--3.3.14.4	Lane Usage Status
rmcMLUsageStatus  OBJECT-TYPE
SYNTAX   INTEGER { 
   notUsed (1),
   schemeF (2),
   schemeO (3),
   schemeFO (4),
   schemeS (5),
   schemeFS (6),
   schemeOS (7),
   schemeFOS (8) }
ACCESS  read-only
STATUS   mandatory
DESCRIPTION
"Indicates which mainline station traffic parameters use the data from this 
lane. If the value of the rmcMLUsageMode-object is NOT 'determinedByOthers', 
then the value is determined directly by that mode object. If, however, the 
value is 'determinedByOthers', then the value is determined by the 
TimeBaseControl mechanism. The values are:
notUsed - the mainline lane traffic parameters are not used for averaging calculation.
schemeF - the lane data will be used to calculate the rmcAverageFlowRate-object.
schemeO - the lane data will be used to calculate the rmcAverageOccupancy-object.
schemeFO - the lane data will be used to calculate the rmcAverageFlowRate-object and rmcAverageOccupancy-object.
schemeS - the lane data will be used to calculate the rmcAverageSpeed-object.
schemeFS - the lane data will be used to calculate the rmcAverageFlowRate-object and rmcAverageSpeed-object.
schemeOS - the lane data will be used to calculate the rmcAverageOccupancy-object and rmcAverageSpeed-object.
schemeFOS - the lane data will be used to calculate the rmcAverageFlowRate-object, rmcAverageOccupancy-object and rmcAverageSpeed-object.
<Object Identifier> 1.3.6.1.4.1.1206.4.2.2.2.8.1.4"
REFERENCE
"See Clause A.2.1 and A.4"
::={ rmcMLStatEntry 4 }

--3.3.14.5	Historic Leading Detector Status
rmcMLHistLeadStatus  OBJECT-TYPE
SYNTAX   INTEGER (0..65535) -- BITMAP16
ACCESS   read-only
STATUS   mandatory
DESCRIPTION
"Indicates the cumulative status of the leading detector. The values are:
<FORMAT>  
Bit Number  Name        Description
Bit 15:     reserved.
Bit 14:     reserved.
Bit 13:     reserved.
Bit 12:     reserved.
Bit 11:     reserved.
Bit 10:     reserved.
Bit 09:     reserved.
Bit 08:     reserved.
Bit 07:     Flow-based No Activity - the rmcMLLeadStatus-object has or had
                        a value of 'flowBasedNoActivity' since reset.
Bit 06:     Error at Sensor - the rmcMLLeadStatus-object has or had
                        a value of 'ErrorAtSensor' since reset.
Bit 05:     No activity - the rmcMLLeadStatus-object has or had
                        a value of 'noActivity' since reset.
Bit 04:     Max presence - the rmcMLLeadStatus-object has or had
                        a value of 'maxPresence' since reset.
Bit 03:     Erratic count - the rmcMLLeadStatus-object has or had
                        a value of 'erraticCount' since reset.
Bit 02:     Other error - the rmcMLLeadStatus-object has or had
                        a value of 'otherError' since reset.
Bit 01:     Working     - the rmcMLLeadStatus-object has or had
                        a value of 'Working' since reset.
Bit 00:     Disabled    - the rmcMLLeadStatus-object has or had
                        a value of 'Disabled' since reset.

In the context of this object, 'reset' means either an initialization of the 
RMC or a successful SET of the rmcHistDetectorReset-object. When a 'reset' 
occurs, all bits shall be set to 0.

If a bit is set to 0, the condition indicated by the bit is false; if it is 
set to 1, the condition is true. 
All reserved bits shall always be set to 'zero' (0). A bad value error shall 
be returned, if a management application writes a one (1) to any of the 
reserved bits.

<Object Identifier> 1.3.6.1.4.1.1206.4.2.2.2.8.1.5"
REFERENCE
"See Clause A.2.1"
::={ rmcMLStatEntry 5 }

--3.3.14.6	Historical Trailing Detector Status
rmcMLHistTrailStatus  OBJECT-TYPE
SYNTAX   INTEGER (0..65535) -- BITMAP16
ACCESS   read-only
STATUS   mandatory
DESCRIPTION
"Indicates the cumulative status of the trailing detector. The status are:
<Format> 
Bit Number  Name        Description
Bit 15:     reserved.
Bit 14:     reserved.
Bit 13:     reserved.
Bit 12:     reserved.
Bit 11:     reserved.
Bit 10:     reserved.
Bit 09:     reserved.
Bit 08:     reserved.
Bit 07:     Flow-based No Activity - the rmcMLTrailStatus-object has or had
                        a value of 'flowBasedNoActivity' since reset.
Bit 06:     Error at Sensor - the rmcMLTrailStatus-object has or had
                        a value of 'Disabled' since reset.
Bit 05:     No activity - the rmcMLTrailStatus-object has or had
                        a value of 'noActivity' since reset.
Bit 04:     Max presence - the rmcMLTrailStatus-object has or had
                        a value of 'maxPresence' since reset.
Bit 03:     Erratic count - the rmcMLTrailStatus-object has or had
                        a value of 'erraticCount' since reset.
Bit 02:     Other error - the rmcMLTrailStatus-object has or had
                        a value of 'otherError' since reset.
Bit 01:     Working     - the rmcMLTrailStatus-object has or had
                        a value of 'Working' since reset.
Bit 00:     Disabled    - the rmcMLTrailStatus-object has or had
                        a value of 'Disabled' since reset.

In the context of this object, 'reset' means either an initialization of the 
RMC or a successful SET of the rmcHistDetectorReset-object. When a 'reset' 
occurs, all bits shall be set to 0.

If a bit is set to 0, the condition indicated by the bit is not true; if it 
is set to 1, the condition is true. 
All reserved bits shall always be set to zero (0)'. A bad value error shall 
be returned, if a management application writes a one (1) to any of the 
reserved bits.

<Object Identifier> 1.3.6.1.4.1.1206.4.2.2.2.8.1.6"
REFERENCE
"See Clause A.2.1"
::={ rmcMLStatEntry 6 }

--3.3.15	Mainline Flow-based No Activity Duration Parameter
rmcFlowBasedNoActivityDuration  OBJECT-TYPE
SYNTAX   INTEGER (0..255)
ACCESS   read-only
STATUS   mandatory
DESCRIPTION
"Indicates the duration of time over which no activity shall be detected on a mainline lane detector prior to its status being set to 'flowBasedNoActivity'. This value is copied from the rmcFlowBasedNoActivityInterval object into this object, when that value becomes active/operational.
<Unit> minute
<Object Identifier> 1.3.6.1.4.1.1206.4.2.2.2.15"
REFERENCE
"See Clause A.4.2"
::={ rmcML 15 }

--3.4	Metered Lane Configuration, Control And Status Node
rmcMeter  OBJECT IDENTIFIER ::={ ramp 3 }

-- This node is an identifier used to group all objects for the configuration,
-- control and status of the metered lanes that are common to all ramp 
-- meter control units.

--3.4.1	Metered Lane Main Configuration node
rmcMeterMain  OBJECT IDENTIFIER ::={ rmcMeter 1 }

-- This node is an identifier used to group the main objects for the 
-- configuration, control and status of the metered lanes that are 
-- common to all ramp meter control units.

--3.4.1.1	Maximum Number of Metered Lanes
rmcMaxNumMeteredLanes   OBJECT-TYPE
SYNTAX   INTEGER (1..255)
ACCESS   read-only
STATUS   mandatory
DESCRIPTION 
"Indicates the maximum number of metered lanes that can be stored in the Metered Lane Configuration Table, and, by association, in all other metered lane tables.
<Unit> number
<Object Identifier> 1.3.6.1.4.1.1206.4.2.2.3.1.1"
REFERENCE
"See Clause A.2.2"
::={ rmcMeterMain 1 }
-- USERS TAKE NOTE OF MULTIPLE VERSIONS -
-- the INTEGER range was changed to start at 1 instead of 0. This 
-- does not cause backwards compatibility problems because this object would 
-- not have been supported, if the function was not supported in the device.

--3.4.1.2	Number of Metered Lanes
rmcNumMeteredLanes   OBJECT-TYPE
SYNTAX   INTEGER (1..255)
ACCESS   read-only
STATUS   mandatory
DESCRIPTION 
"Indicates the actual number of metered lanes that are present in the Metered Lane Configuration Table, and, by association, in all other metered lane tables. This value shall not exceed the value of the rmcMaxNumMeteredLanes-object.
<Unit> number
<Object Identifier> 1.3.6.1.4.1.1206.4.2.2.3.1.2"
REFERENCE
"See Clause A.2.2"
::={ rmcMeterMain 2 }
-- USERS TAKE NOTE OF MULTIPLE VERSIONS -
-- the INTEGER range was changed to start at 1 instead of 0. This
-- does not cause backwards compatibility problems because this object would
-- not have been supported, if the function was not supported in the device.

--3.4.1.3	Metered Lane Configuration Table
rmcMeterCfgTable OBJECT-TYPE
SYNTAX   SEQUENCE OF RmcMeterCfgEntry
ACCESS   not-accessible
STATUS   mandatory
DESCRIPTION 
"A table containing the configuration information for a metered lane.
<Table Type> static
<Object Identifier> 1.3.6.1.4.1.1206.4.2.2.3.1.3"
::={ rmcMeterMain 3 }

rmcMeterCfgEntry OBJECT-TYPE
SYNTAX   RmcMeterCfgEntry
ACCESS   not-accessible
STATUS   mandatory
DESCRIPTION 
"Configuration parameters of the metered lane table. This table is directly correlated to the Metered Lane Control Table, which means that the number of rows in this table is exactly the same as the number of rows in the Metered Lane Control Table (AUGMENT TABLE in SNMPv2 terminology). Table management can only take place through the Metered Lane Control Table, while this table provides configuration parameters for the associated metered lane.
<TableType> static
<Object Identifier> 1.3.6.1.4.1.1206.4.2.2.3.1.3.1"
INDEX { rmcMeterNumber }
::={ rmcMeterCfgTable 1 }

RmcMeterCfgEntry ::=SEQUENCE { 
	rmcMeterNumber               INTEGER,

	rmcDependGroupNumber         INTEGER,
	rmcDependGroupSeqNumber      INTEGER,
	rmcCmdSourcePriorityOrder    INTEGER,

	rmcDemandErraticCount        INTEGER,
	rmcDemandMaxPresence         INTEGER,
	rmcDemandNoActivity          INTEGER,

	rmcMinMeterTime              INTEGER,
	rmcMinNonMeterTime           INTEGER,
	rmcAbsoluteMinMeterRate      INTEGER,
	rmcAbsoluteMaxMeterRate      INTEGER,
	rmcSystemMinMeterRate        INTEGER,
	rmcSystemMaxMeterRate        INTEGER,

	rmcStartAlert                INTEGER,
	rmcStartWarning              INTEGER,
	rmcStartGreen                INTEGER,
	rmcStartGapTime              INTEGER,
	rmcStartGapQueueDetectorNum  INTEGER,
	rmcStartYellow               INTEGER,
	rmcStartRed                  INTEGER,

	rmcMinRed                    INTEGER,
	rmcRedViolationClearance     INTEGER,
	rmcRedViolationAdjust        INTEGER,
	rmcMinGreen                  INTEGER,
	rmcMaxGreen                  INTEGER,
	rmcYellow                    INTEGER,
	rmcShortStopTime             INTEGER,
	rmcShortStopOccupancy        INTEGER,
	rmcShortStopQueueDetectorNum INTEGER,
	rmcLongStopTime              INTEGER,

	rmcDemandGap                 INTEGER,
	rmcDemandRed                 INTEGER,

	rmcShutNormalRate            INTEGER,
	rmcShutWarning               INTEGER,
	rmcShutTime                  INTEGER,
	rmcPostMeterGreen            INTEGER,

	rmcQueueViolationFlag        INTEGER,
	rmcQueueShutdownFlag         INTEGER,
	rmcQueueAdjustUsage          INTEGER,

	rmcDemandDependMaxPresence   INTEGER, -- added in version 2
	rmcDemandDependNoActivity    INTEGER  -- added in version 2
    }

--3.4.1.3.1	Metered Lane Number
rmcMeterNumber   OBJECT-TYPE
SYNTAX   INTEGER (1..255)
ACCESS   read-only
STATUS   mandatory
DESCRIPTION
"Enumerated listing of the metered lanes. 
This value shall not exceed the value stated in the rmcMaxNumMeteredLanes-object.
<Unit> number
<Object Identifier> 1.3.6.1.4.1.1206.4.2.2.3.1.3.1.1"
REFERENCE
"See Clause A.2.2, A.8.3.1.3 and A.8.5.3.3"
::={ rmcMeterCfgEntry 1 }

--3.4.1.3.2	Dependency Group Number
rmcDependGroupNumber OBJECT-TYPE
SYNTAX   INTEGER (1..255)
ACCESS   read-write
STATUS   mandatory
DESCRIPTION
"Indicates the dependency group with which this metered lane is associated. 
This value shall not exceed the value of the rmcMaxNumDependGroup-object.
<Unit> number
<Object Identifier> 1.3.6.1.4.1.1206.4.2.2.3.1.3.1.2"
REFERENCE
"See Clause A.2.2"
::={ rmcMeterCfgEntry 2 }

--3.4.1.3.3	Dependency Group Sequence Number
rmcDependGroupSeqNumber   OBJECT-TYPE
SYNTAX   INTEGER (1..255)
ACCESS   read-write
STATUS   mandatory
DESCRIPTION
"Indicates the unique position of this metered lane within its dependency group which determines the Ramp Lane Sequence.
<Unit> number
<Object Identifier> 1.3.6.1.4.1.1206.4.2.2.3.1.3.1.3"
REFERENCE
"See Clause A.2.3.2"
::={ rmcMeterCfgEntry 3 }

--3.4.1.3.4	Command Source Priority Order
rmcCmdSourcePriorityOrder   OBJECT-TYPE
SYNTAX   INTEGER {
   schemeCIT (1),
   schemeICT (2),
   schemeTCI (3),
   schemeTIC (4),
   schemeCTI (5),
   schemeITC (6) }
ACCESS   read-write
STATUS   mandatory
DESCRIPTION 
"Indicates the active command source priority order for this metered lane. 
The values are:
schemeCIT -in decreasing order: manual, communications, interconnect, timebase control, default;
schemeICT -in decreasing order: manual, interconnect, communications, timebase control, default;
schemeTCI -in decreasing order: manual, timebase control, communications, interconnect, default;
schemeTIC -in decreasing order: manual, timebase control, interconnect, communications, default;
schemeCTI -in decreasing order: manual, communications, timebase control, interconnect, default;
schemeITC -in decreasing order: manual, interconnect, timebase control, communications, default.
<Object Identifier> 1.3.6.1.4.1.1206.4.2.2.3.1.3.1.4"
REFERENCE
"See Clause A.3"
::={ rmcMeterCfgEntry 4 }

--3.4.1.3.5	Demand Detector Erratic Count Threshold
rmcDemandErraticCount   OBJECT-TYPE
SYNTAX   INTEGER (0..255)
ACCESS   read-write
STATUS   mandatory
DESCRIPTION 
"If the vehicle count, over the most recently completed calculation interval,on the demand detector for a metered lane exceeds this threshold, the rmcDemandStatus-object for that metered lane shall be set to a value of 'erraticCount'. 
This value shall be expressed in 1-vehicle increments. 
A suggested usable range is 0 to 30. 
A value of zero (0) shall inhibit the erratic count testing.
<Unit> number
<Object Identifier> 1.3.6.1.4.1.1206.4.2.2.3.1.3.1.5"
REFERENCE
"See Clause A.2.2.1"
::={ rmcMeterCfgEntry 5 }

--3.4.1.3.6	Demand Detector Maximum Presence Threshold
rmcDemandMaxPresence   OBJECT-TYPE
SYNTAX   INTEGER (0..65535)
ACCESS   read-write
STATUS   mandatory
DESCRIPTION 
"If the input on the demand detector for a  metered lane has been continuously actuated for longer than the time indicated by this threshold, the rmcDemandStatus-object for that metered lane shall be set to a value of 'maxPresence'. 
This value shall be expressed in 1-minute increments. 
A suggested usable range is 0 to 1500. 
A value of zero (0) shall inhibit the maximum presence testing.
<Unit> minute
<Object Identifier> 1.3.6.1.4.1.1206.4.2.2.3.1.3.1.6"
REFERENCE
"See Clause A.2.2.1"
::={ rmcMeterCfgEntry 6 }

--3.4.1.3.7	Demand Detector No Activity Threshold
rmcDemandNoActivity   OBJECT-TYPE
SYNTAX   INTEGER (0..65535)
ACCESS   read-write
STATUS   mandatory
DESCRIPTION 
"If the input on the demand detector for a  metered lane has not been actuated for longer than the time indicated by this threshold, the 
rmcDemandStatus-object for that metered lane shall be set to a value of 'noActivity'.
This value shall be expressed in 1-minute increments.
A suggested usable range is 0 to 1500.
A value of zero (0) shall inhibit the no activity testing.
<Unit> minute
<Object Identifier> 1.3.6.1.4.1.1206.4.2.2.3.1.3.1.7"
REFERENCE
"See Clause A.2.2.1"
::={ rmcMeterCfgEntry 7 }

--3.4.1.3.8	Minimum Metering Time
rmcMinMeterTime   OBJECT-TYPE
SYNTAX   INTEGER (0..255)
ACCESS   read-write
STATUS   mandatory
DESCRIPTION
"Indicates the  minimum length of  the metering state. This will prevent excessive cycling of the ramp meter between the metering and non-metering states.
This value shall be expressed in 1-minute increments.
A suggested usable range is 0 to 60.
<Unit> minute
<Object Identifier> 1.3.6.1.4.1.1206.4.2.2.3.1.3.1.8"
REFERENCE
"See Clause A.6"
::={ rmcMeterCfgEntry 8 }

--3.4.1.3.9	Minimum Non-Metering Time
rmcMinNonMeterTime   OBJECT-TYPE
SYNTAX   INTEGER (0..255)
ACCESS   read-write
STATUS   mandatory
DESCRIPTION
"Indicates the  minimum length of the non-metering state. This will prevent excessive cycling of the ramp meter between the metering and non-metering states.
This value shall be expressed in 1-minute increments.
A suggested usable range is 0 to 60.
<Unit> minute
<Object Identifier> 1.3.6.1.4.1.1206.4.2.2.3.1.3.1.9"
REFERENCE
"See Clause A.5"
::={ rmcMeterCfgEntry 9 }

--3.4.1.3.10	Absolute Minimum Metering Rate
rmcAbsoluteMinMeterRate   OBJECT-TYPE
SYNTAX   INTEGER (0..65535)
ACCESS   read-write
STATUS   mandatory
DESCRIPTION
"Indicates the absolute minimum metering rate.
This value shall be expressed in 1-vph increments.
A suggested usable range is 0, 120 to 1800.
A value of zero (0) indicates this parameter shall not be used.
<Unit> vehicles per hour
<Object Identifier> 1.3.6.1.4.1.1206.4.2.2.3.1.3.1.10"
REFERENCE
"See Clause A.2.2"
::={ rmcMeterCfgEntry 10 }

--3.4.1.3.11	Absolute Maximum Metering Rate
rmcAbsoluteMaxMeterRate   OBJECT-TYPE
SYNTAX   INTEGER (0..65535)
ACCESS   read-write
STATUS   mandatory
DESCRIPTION
"Indicates the absolute maximum metering rate.
This value shall be expressed in 1-vph increments.
A suggested usable range is 0, 120 to 1800. 
A value of zero (0) indicates this parameter shall not be used.
The value, if non-zero, shall be greater than or equal to the value of the 
rmcAbsoluteMinMeterRate-object.
<Unit> vehicles per hour
<Object Identifier> 1.3.6.1.4.1.1206.4.2.2.3.1.3.1.11"
REFERENCE
"See Clause A.2.2"
::={ rmcMeterCfgEntry 11 }

--3.4.1.3.12	System Minimum Metering Rate
rmcSystemMinMeterRate   OBJECT-TYPE
SYNTAX   INTEGER (0..65535)
ACCESS   read-write
STATUS   mandatory
DESCRIPTION
"Indicates the system minimum metering rate. 
This value shall be expressed in 1-vph increments.
A suggested usable range is 0, 120 to 1800.
A value of zero (0) indicates this parameter shall not be used.
<Unit> vehicles per hour
<Object Identifier> 1.3.6.1.4.1.1206.4.2.2.3.1.3.1.12"
REFERENCE
"See Clause A.2.2"
::={ rmcMeterCfgEntry 12 }

--3.4.1.3.13	System Maximum Metering Rate
rmcSystemMaxMeterRate   OBJECT-TYPE
SYNTAX   INTEGER (0..65535)
ACCESS   read-write
STATUS   mandatory
DESCRIPTION
"Indicates the system maximum metering rate.
This value shall be expressed in 1-vph increments.
A suggested usable range is 0, 120 to 1800. 
A value of zero (0) indicates this parameter shall not be used.
The value, if non-zero, shall be greater than or equal to the value of the 
rmcSystemMinMeterRate-object.
<Unit> vehicles per hour
<Object Identifier> 1.3.6.1.4.1.1206.4.2.2.3.1.3.1.13"
REFERENCE
"See Clause A.2.2"
::={ rmcMeterCfgEntry 13 }

--3.4.1.3.14	Startup Alert Time
rmcStartAlert   OBJECT-TYPE
SYNTAX   INTEGER (0..65535)
ACCESS   read-write
STATUS   mandatory
DESCRIPTION
"Indicates the length of the startup alert interval.
This value shall be expressed in 0.1-second increments (i.e, 40 = 4.0 seconds).
A suggested usable range is 0 to 600.
A value of zero (0) shall cause the metered lane to bypass this interval.
<Unit> tenth of second
<Object Identifier> 1.3.6.1.4.1.1206.4.2.2.3.1.3.1.14"
REFERENCE
"See Clause A.8.2.1"
::={ rmcMeterCfgEntry 14 }

--3.4.1.3.15	Startup Warning Time
rmcStartWarning   OBJECT-TYPE
SYNTAX   INTEGER (0..65535)
ACCESS   read-write
STATUS   mandatory
DESCRIPTION
"Indicates the length of the startup warning interval.
This value shall be expressed in 0.1-second increments (i.e, 40 = 4.0 seconds).
A suggested usable range is 0 to 600.
A value of zero (0) shall cause the metered lane to bypass this interval.
<Unit> tenth of second
<Object Identifier> 1.3.6.1.4.1.1206.4.2.2.3.1.3.1.15"
REFERENCE
"See Clause A.8.2.2"
::={ rmcMeterCfgEntry 15 }

--3.4.1.3.16	Startup Green Time
rmcStartGreen   OBJECT-TYPE
SYNTAX   INTEGER (0..65535)
ACCESS   read-write
STATUS   mandatory
DESCRIPTION
"Indicates the length of the startup green interval.
This value shall be expressed in 0.1-second increments (i.e, 40 = 4.0 seconds).
A suggested usable range is 0 to 600.
A value of zero (0) shall cause the metered lane to bypass this interval.
<Unit> tenth of second
<Object Identifier> 1.3.6.1.4.1.1206.4.2.2.3.1.3.1.16"
REFERENCE
"See Clause A.8.2.3"
::={ rmcMeterCfgEntry 16 }

--3.4.1.3.17	Startup Gap Time
rmcStartGapTime   OBJECT-TYPE
SYNTAX   INTEGER (0..255)
ACCESS   read-write
STATUS   mandatory
DESCRIPTION
"Indicates the length of time between successive actuations of the detector 
identified by the rmcStartGapQueueDetectorNum-object necessary to terminate 
the startup green interval.
This value shall be expressed in 0.1-second increments  (i.e, 40 = 4.0 seconds).
A suggested usable range is 0 and 10 to 150.
A value of zero (0) shall make the termination of the interval dependent only 
on value of the rmcStartGreen-object.
<Unit> tenth of second
<Object Identifier> 1.3.6.1.4.1.1206.4.2.2.3.1.3.1.17"
REFERENCE
"See Clause A.8.2.3"
::={ rmcMeterCfgEntry 17 }

--3.4.1.3.18	Startup Gap Queue Detector Number
rmcStartGapQueueDetectorNum   OBJECT-TYPE
SYNTAX   INTEGER (0..255)
ACCESS   read-write
STATUS   mandatory
DESCRIPTION
"Indicates the queue detector that is used for startup gap calculations. 
The value of this object cannot be larger than the value of the rmcNumQueueEntries-object.
<Unit> number
<Object Identifier> 1.3.6.1.4.1.1206.4.2.2.3.1.3.1.18"
REFERENCE
"See Clause A.8.2.3"
::={ rmcMeterCfgEntry 18 }

--3.4.1.3.19	Startup Yellow Time
rmcStartYellow   OBJECT-TYPE
SYNTAX   INTEGER (0..255)
ACCESS   read-write
STATUS   mandatory
DESCRIPTION
"Indicates the length of the startup yellow interval. 
This value shall be expressed in 0.1-second increments (i.e, 40 = 4.0 seconds).
A suggested usable range is 0 and 20 to 100.
A value of zero (0) shall cause the metered lane to bypass this interval.
<Unit> tenth of second
<Object Identifier> 1.3.6.1.4.1.1206.4.2.2.3.1.3.1.19"
REFERENCE
"See Clause A.8.2.4"
::={ rmcMeterCfgEntry 19 }

--3.4.1.3.20	Startup Red Time
rmcStartRed   OBJECT-TYPE
SYNTAX   INTEGER (0..255)
ACCESS   read-write
STATUS   mandatory
DESCRIPTION
"Indicates the length of the startup red interval.
This value shall be expressed in 0.1-second increments (i.e, 40 = 4.0 seconds).
A suggested usable range is 20 to 100.
A value of zero (0) shall cause the metered lane to bypass this interval.
<Unit> tenth of second
<Object Identifier> 1.3.6.1.4.1.1206.4.2.2.3.1.3.1.20"
REFERENCE
"See Clause A.8.2.5"
::={ rmcMeterCfgEntry 20 }

--3.4.1.3.21	Minimum Red Time
rmcMinRed   OBJECT-TYPE
SYNTAX   INTEGER (0..255)
ACCESS   read-write
STATUS   mandatory
DESCRIPTION
"Indicates the minimum length of the red interval. 
This value shall be expressed in 0.1-second increments (i.e, 40 = 4.0 seconds).
A suggested usable range is 10 to 150.
<Unit> tenth of second
<Object Identifier> 1.3.6.1.4.1.1206.4.2.2.3.1.3.1.21"
REFERENCE
"See Clause A.8.3.1.1 and A.8.5.3.1"
::={ rmcMeterCfgEntry 21 }

--3.4.1.3.22	Red Violation Clearance Time
rmcRedViolationClearance   OBJECT-TYPE
SYNTAX   INTEGER (0..255)
ACCESS   read-write
STATUS   mandatory
DESCRIPTION
"Indicates the length of time that has to elapse during the red interval before a red light violation can be detected.
This value shall be expressed in 0.1-second increments (i.e, 40 = 4.0 seconds).
A suggested usable range is 0 to 50.
A value of zero (0) indicates that no red light violations shall be detected.
<Unit> tenth of second
<Object Identifier> 1.3.6.1.4.1.1206.4.2.2.3.1.3.1.22"
REFERENCE
"See Clause A.8.3.1.2 and A.8.5.3.2"
::={ rmcMeterCfgEntry 22 }

--3.4.1.3.23	Red Violation Adjustment Time
rmcRedViolationAdjust   OBJECT-TYPE
SYNTAX   INTEGER (0..255)
ACCESS   read-write
STATUS   mandatory
DESCRIPTION
"Indicates the length of time by which the current cycle will be extended for each red light violation.
This value shall be expressed in 0.1-second increments (i.e, 
40 = 4.0 seconds).
A suggested usable range is 10 to 50.
<Unit> tenth of second
<Object Identifier> 1.3.6.1.4.1.1206.4.2.2.3.1.3.1.23"
REFERENCE
"See Clause A.8.3.1.2 and A.8.5.3.2"
::={ rmcMeterCfgEntry 23 }

--3.4.1.3.24	Minimum Green Time
rmcMinGreen   OBJECT-TYPE
SYNTAX   INTEGER (0..255)
ACCESS   read-write
STATUS   mandatory
DESCRIPTION
"Indicates the minimum length of the green interval.
This value shall be expressed in 0.1-second increments (i.e, 40 = 4.0 seconds).
A suggested usable range is 10 to 50.
<Unit> tenth of second
<Object Identifier> 1.3.6.1.4.1.1206.4.2.2.3.1.3.1.24"
REFERENCE
"See Clause A.8.3.2.2 and A.8.5.1.2"
::={ rmcMeterCfgEntry 24 }

--3.4.1.3.25	Maximum Green Time
rmcMaxGreen   OBJECT-TYPE
SYNTAX   INTEGER (0..255)
ACCESS   read-write
STATUS   mandatory
DESCRIPTION
"Indicates the maximum length of the green interval.
This value shall be expressed in 0.1-second increments (i.e, 40 = 4.0 seconds).
A suggested usable range is 10 to 150.
<Unit> tenth of second
<Object Identifier> 1.3.6.1.4.1.1206.4.2.2.3.1.3.1.25"
REFERENCE
"See Clause A.8.3.2.3"
::={ rmcMeterCfgEntry 25 }

--3.4.1.3.26	Yellow Time
rmcYellow   OBJECT-TYPE
SYNTAX   INTEGER (0..255)
ACCESS   read-write
STATUS   mandatory
DESCRIPTION
"Indicates the length of the yellow interval.
This value shall be expressed in 0.1-second increments (i.e, 40 = 4.0 seconds).
A suggested usable range is 0 and 5 to 50.
A value of zero (0) shall cause the metered lane to bypass this interval.
<Unit> tenth of second
<Object Identifier> 1.3.6.1.4.1.1206.4.2.2.3.1.3.1.26"
REFERENCE
"See Clause A.8.3.2.1, A.3.3, A.8.5.1.1 and A.8.5.2"
::={ rmcMeterCfgEntry 26 }

--3.4.1.3.27	Short Stop Time
rmcShortStopTime   OBJECT-TYPE
SYNTAX   INTEGER (0..65535)
ACCESS   read-write
STATUS   mandatory
DESCRIPTION
"Indicates the length of time that has to elapse after the red interval has expired before a short stop condition can be detected.
This value shall be expressed in 0.1-second increments (i.e, 40 = 4.0 seconds).
A suggested usable range is 0 and 10 to 1200.
A value of zero (0) shall inhibit short stop termination of the Red Interval.
<Unit> tenth of second
<Object Identifier> 1.3.6.1.4.1.1206.4.2.2.3.1.3.1.27"
REFERENCE
"See Clause A.8.3.1.4.2 and A.8.5.3.4.2"
::={ rmcMeterCfgEntry 27 }

--3.4.1.3.28	Short Stop Occupancy Threshold
rmcShortStopOccupancy   OBJECT-TYPE
SYNTAX   INTEGER (0..65535)
ACCESS   read-write
STATUS   mandatory
DESCRIPTION
"Indicates the occupancy threshold at the detector identified by the rmcShortStopQueueDetectorNum-object, meaning that this detector is used to detect short stop conditions. 
This value shall be expressed in 0.1-percent increments (i.e, 40 = 4.0 percent). 
A suggested usable range is 0 to 1000.
<Unit> tenth of percent
<Object Identifier> 1.3.6.1.4.1.1206.4.2.2.3.1.3.1.28"
REFERENCE
"See Clause A.8.3.1.4.2 and A.8.5.3.4.2"
::={ rmcMeterCfgEntry 28 }

--3.4.1.3.29	Short Stop Queue Detector Number
rmcShortStopQueueDetectorNum   OBJECT-TYPE
SYNTAX   INTEGER (0..255)
ACCESS   read-write
STATUS   mandatory
DESCRIPTION
"Indicates the queue detector that is used for short stop calculations. 
The value of this object cannot be larger than the value of the rmcNumQueueEntries-object.
<Unit> number
<Object Identifier> 1.3.6.1.4.1.1206.4.2.2.3.1.3.1.29"
REFERENCE
"See Clause A.8.3.1.4.2"
::={ rmcMeterCfgEntry 29 }

--3.4.1.3.30	Long Stop Time
rmcLongStopTime   OBJECT-TYPE
SYNTAX   INTEGER (0..255)
ACCESS   read-write
STATUS   mandatory
DESCRIPTION
"Indicates the length of time that has to elapse after the red interval has expired before a long stop condition can be detected. 
This value shall be expressed in 0.1-second increments (i.e, 40 = 4.0 seconds). 
A suggested usable range is 0 and 10 to 100. 
A value of zero (0) shall inhibit long stop termination of the Red interval.
<Unit> tenth of second
<Object Identifier> 1.3.6.1.4.1.1206.4.2.2.3.1.3.1.30"
REFERENCE
"See Clause A.8.3.1.4.3 and A.8.5.3.4.3"
::={ rmcMeterCfgEntry 30 }

--3.4.1.3.31	Demand Gap Time
rmcDemandGap   OBJECT-TYPE
SYNTAX   INTEGER (0..255)
ACCESS   read-write
STATUS   mandatory
DESCRIPTION
"Indicates the length of time that has to elapse after the green interval has expired without actuation of the demand detector before a demand gap condition can be detected. 
This value shall be expressed in 0.1-second increments (i.e, 40 = 4.0 seconds). 
A suggested usable range is 10 to 50.
<Unit> tenth of second
<Object Identifier> 1.3.6.1.4.1.1206.4.2.2.3.1.3.1.31"
REFERENCE
"See Clause A.8.3.1.4.4 and A.8.5.3.4.4"
::={ rmcMeterCfgEntry 31 }

--3.4.1.3.32	Demand Red Time
rmcDemandRed   OBJECT-TYPE
SYNTAX   INTEGER (0..255)
ACCESS   read-write
STATUS   mandatory
DESCRIPTION
"Indicates the length of time by which the current red interval will be 
extended once the demand detector is actuated after the detection of a demand gap condition. 
This value shall be expressed in 0.1-second increments (i.e, 40 = 4.0 seconds). 
A suggested usable range is 0 and 10 to 150. 
A value of zero (0) shall inhibit demand red extension of the current cycle.
<Unit> tenth of second
<Object Identifier> 1.3.6.1.4.1.1206.4.2.2.3.1.3.1.32"
REFERENCE
"See Clause A.8.3.1.4.4 and A.8.5.3.4.4"
::={ rmcMeterCfgEntry 32 }

--3.4.1.3.33	Shutdown Normal Metering Rate
rmcShutNormalRate   OBJECT-TYPE
SYNTAX   INTEGER (0..65535)
ACCESS   read-write
STATUS   mandatory
DESCRIPTION
"Indicates the metering rate during shutdown when the rmcImplementAction- object has a value of either 'dark' or 'restInGreen'. 
This value shall be expressed in 1-vph increments. 
A suggested usable range is 120 to 1800.
<Unit> vehicles per hour
<Object Identifier> 1.3.6.1.4.1.1206.4.2.2.3.1.3.1.33"
REFERENCE
"See Clause A.6.1"
::={ rmcMeterCfgEntry 33 }

--3.4.1.3.34	Shutdown Warning Time
rmcShutWarning   OBJECT-TYPE
SYNTAX   INTEGER (0..65535)
ACCESS   read-write
STATUS   mandatory
DESCRIPTION
"Indicates the length of the shutdown warning interval. 
This value shall be expressed in 0.1-second increments (i.e, 40 = 4.0 seconds). 
A suggested usable range is 0 to 600. 
A value of zero (0) shall cause the metered lane to bypass this interval.
<Unit> tenth of second
<Object Identifier> 1.3.6.1.4.1.1206.4.2.2.3.1.3.1.34"
REFERENCE
"See Clause A.8.5.4"
::={ rmcMeterCfgEntry 34 }
-- USERS TAKE NOTE OF MULTIPLE VERSIONS -
-- the INTEGER range was changed to end at 65535 instead of 255. 
-- This does not cause backwards compatibility problems because the value 
-- range of this object was expanded, which is allowed according to SNMP 
-- rules.

--3.4.1.3.35	Shutdown Time
rmcShutTime   OBJECT-TYPE
SYNTAX   INTEGER (0..65535)
ACCESS   read-write
STATUS   mandatory
DESCRIPTION
"Indicates the minimum length of shutdown metering. 
This value shall be expressed in 1-second increments. 
A suggested usable range is 0 to 600.
<Unit> second
<Object Identifier> 1.3.6.1.4.1.1206.4.2.2.3.1.3.1.35"
REFERENCE
"See Clause A.8.5.3.5"
::={ rmcMeterCfgEntry 35 }

--3.4.1.3.36	Post-metering Green Time
rmcPostMeterGreen   OBJECT-TYPE
SYNTAX   INTEGER (0..65535)
ACCESS   read-write
STATUS   mandatory
DESCRIPTION
"Indicates the length of the Post-metering Green interval. 
This value shall be expressed in 0.1-second increments (i.e, 40 = 4.0 seconds). 
A suggested usable range is 0 to 600. 
A value of zero (0) shall cause the metered lane to bypass this interval.
<Unit> tenth of second
<Object Identifier> 1.3.6.1.4.1.1206.4.2.2.3.1.3.1.36"
REFERENCE
"See Clause A.8.6.1"
::={ rmcMeterCfgEntry 36 }

--3.4.1.3.37	Queue versus Violations Flag
rmcQueueViolationFlag   OBJECT-TYPE
SYNTAX   INTEGER (0..1)
ACCESS   read-write
STATUS   mandatory
DESCRIPTION
"Indicates whether queue adjustment will supersede red violations.
0=false - indicates that both queue and red violation adjustments may be performed simultaneously.
1=true - indicates that queue adjustment will supersede red violation adjustment.
<Object Identifier> 1.3.6.1.4.1.1206.4.2.2.3.1.3.1.37"
REFERENCE
"See Clause A.8.3.1.2"
DEFVAL
{ 0 }
::={ rmcMeterCfgEntry 37 }

--3.4.1.3.38	Queue versus Shutdown Flag
rmcQueueShutdownFlag   OBJECT-TYPE
SYNTAX   INTEGER (0..1)
ACCESS   read-write
STATUS   mandatory
DESCRIPTION
"Indicates whether queue override takes precedence over shutdown metering.
0= false - allows the transition to the non-metering state regardless of queue override adjustments.
1= true - requires the queue override adjustments be completed before the transition to the non-metering state can begin.
<Object Identifier> 1.3.6.1.4.1.1206.4.2.2.3.1.3.1.38"
REFERENCE
"See Clause A.6"
::={ rmcMeterCfgEntry 38 }

--3.4.1.3.39	Queue Adjustment Usage
rmcQueueAdjustUsage   OBJECT-TYPE
SYNTAX   INTEGER {
   additive (1),
   additiveXI (2),
   priorityXI (3) }
ACCESS   read-write
STATUS   mandatory
DESCRIPTION
"Indicates which queue adjustments are made. 
additive= indicates that a queue adjustment shall be made for each queue 
    detector (both excessive and intermediate queue detectors) whose 
    rmcQueueFlag-object has a value of 'true'.
additiveXI =  indicates that a queue adjustment shall be made for each queue 
    detector whose rmcQueueType-object has a value of 'excessive' and whose 
    rmcQueueFlag-object has a value of 'true'. If no such detectors exist, a 
    queue adjustment shall be made for each queue detector whose rmcQueueType-
    object has a value of 'intermediate' and whose rmcQueueFlag-object has a 
    value of 'true'.
priorityXI =  indicates that a queue adjustment shall be made for the highest 
    entry (lowest index value) queue detector whose rmcQueueType-object has a 
    value of 'excessive' and whose rmcQueueFlag-object has a value of 'true'. 
    If no detector exists that fulfills these requirements, a queue adjustment 
    shall be made for the highest entry (lowest index value) queue detector 
    whose rmcQueueType-object has a value of 'intermediate' and whose 
    rmcQueueFlag-object has a value of 'true'.
<Object Identifier> 1.3.6.1.4.1.1206.4.2.2.3.1.3.1.39"
REFERENCE
"See Clause A.9.2"
::={ rmcMeterCfgEntry 39 }

--3.4.1.3.40	Demand Detector Dependent Maximum Presence Threshold
rmcDemandDependMaxPresence   OBJECT-TYPE
SYNTAX   INTEGER (0..65535)
ACCESS   read-write
STATUS   mandatory
DESCRIPTION 
"If the input on the demand detector for a metered lane has been continuously actuated, while the input on the passage detector for the same metered lane has been continuously non-actuated for longer than this threshold and the rmcPassageMode-object is not 'recalled' and the rmcPassageStatus-object is 'working' and the rmcMergeFlag-object is 'false', the rmcDemandStatus-object for this metered lane shall be set to a value of 'depMaxPresence'.
This value shall be expressed in 1-second increments. 
A suggested usable range is 0 to 600. 
A value of zero (0) shall inhibit the dependent maximum presence testing.
<Unit> second
<Object Identifier> 1.3.6.1.4.1.1206.4.2.2.3.1.3.1.40"
REFERENCE
"See Clause A.2.2.1"
::={ rmcMeterCfgEntry 40 }

--3.4.1.3.41	Demand Detector Dependent No Activity Threshold
rmcDemandDependNoActivity   OBJECT-TYPE
SYNTAX   INTEGER (0..255)
ACCESS   read-write
STATUS   mandatory
DESCRIPTION 
"If the input on the demand detector for a metered lane has not been actuated, while more vehicles than indicated by this threshold have been counted on the passage detector of the same metered lane and the rmcPassageMode-object is not 'recalled' and the rmcPassageStatus-object is 'working', the rmcDemandStatus-object for this metered lane shall be set to a value of 'depNoActivity'. 
This value shall be expressed in 1-vehicle increments. 
A suggested usable range is 0 to 30. 
A value of zero (0) shall inhibit the dependent no activity testing.
<Unit> number
<Object Identifier> 1.3.6.1.4.1.1206.4.2.2.3.1.3.1.41"
REFERENCE
"See Clause A.2.2.1"
::={ rmcMeterCfgEntry 41 }

--3.4.1.4	Metered Lane Control Table
rmcMeterCtrlTable   OBJECT-TYPE
SYNTAX   SEQUENCE OF RmcMeterCtrlEntry
ACCESS   not-accessible
STATUS   mandatory
DESCRIPTION 
"A table containing the control information for a metered lane.
<Table Type> static
<Object Identifier> 1.3.6.1.4.1.1206.4.2.2.3.1.7"
::={ rmcMeterMain 7 }
--Editor's Note: There is a skip in OID at this point, but this was already 
-- present in version 1 and I cannot change the OID in version 2 for any 
-- existing object.

rmcMeterCtrlEntry   OBJECT-TYPE
SYNTAX   RmcMeterCtrlEntry
ACCESS   not-accessible
STATUS   mandatory
DESCRIPTION 
"Control Parameters of the metered lane table. A particular row of this table 
can be managed using the rmcMeterMode-object.
<Object Identifier> 1.3.6.1.4.1.1206.4.2.2.3.1.7.1"
INDEX { rmcMeterNumber }
::={ rmcMeterCtrlTable 1 }

RmcMeterCtrlEntry ::=SEQUENCE {
	rmcMeterMode               INTEGER,
	rmcManualAction            INTEGER,
	rmcManualPlan              INTEGER,
	rmcManualRate              INTEGER,
	rmcManualVehiclesPerGrn    INTEGER,

	rmcIntercoAction           INTEGER,
	rmcIntercoPlan             INTEGER,
	rmcIntercoRate             INTEGER,
	rmcIntercoVehiclesPerGrn   INTEGER,

	rmcCommActionMode          INTEGER, -- modified name only in version 2
	rmcCommPlan                INTEGER,
	rmcCommRate                INTEGER,
	rmcCommVehiclesPerGrn      INTEGER,

	rmcDefaultAction           INTEGER,
	rmcDefaultPlan             INTEGER,
	rmcDefaultRate             INTEGER,
	rmcDefaultVehiclesPerGrn   INTEGER,

	rmcDemandMode              INTEGER,
	rmcPreMeterNonGreen        INTEGER, -- added in version 2
	rmcCritFlowRateThresh      INTEGER, -- added in version 2
	rmcCritOccupancyThresh     INTEGER, -- added in version 2
	rmcCriticalSpeedThreshold  INTEGER -- added in version 2
}

--3.4.1.4.1	Metered Lane Mode
rmcMeterMode   OBJECT-TYPE
SYNTAX   INTEGER (0..1)
ACCESS   read-write
STATUS   mandatory
DESCRIPTION 
"Indicates the mode of the metered lane. The values are:
0 = disabled - the metered lane is not used.
1 = enabled - the metered lane is used.
<Object Identifier> 1.3.6.1.4.1.1206.4.2.2.3.1.7.1"
REFERENCE
"See Clause A.2.2"
::={ rmcMeterCtrlEntry 1 }

--3.4.1.4.2	Manual Action
rmcManualAction   OBJECT-TYPE
SYNTAX   INTEGER {
   dark (1),
   restInGreen (2),
   fixedRate (3),
   trafficResponsive (4),
   emergencyGreen (5),
   skip (6) }
ACCESS   read-write
STATUS   mandatory
DESCRIPTION 
"Indicates the requested action while the value of the 
rmcImplementCommandSource-object is 'manual'. The values are:
dark - indicates that the metered lane will advance to the Pre-Metering Non-
    Green interval.
restInGreen - indicates that the metered lane will advance to the Pre-
    Metering Green interval.
fixedRate - indicates that the metered lane will operate using the value of 
    the rmcManualRate-object.
trafficResponsive -indicates that the metered lane will operate using mainline 
    station traffic conditions and the value of the rmcManualPlan-object.
emergencyGreen - indicates that the metered lane will advance to and remain 
    in the Post-metering Green interval without entering the Shutdown Green, 
    Shutdown Yellow, Shutdown Red or Shutdown Warning intervals when the 
    metered lane is NOT in the Non-metering state. The metered lane will 
    advance to the Pre-Metering Green interval when the metered lane is in 
    the Non-metering state.
skip - indicates that the next-lower level command source shall be considered 
    as specified by the rmcCmdSourcePriorityOrder-object. 
<Object Identifier> 1.3.6.1.4.1.1206.4.2.2.3.1.7.1.2"
REFERENCE
"See Clause A.3"
::={ rmcMeterCtrlEntry 2 }

--3.4.1.4.3	Manual Plan
rmcManualPlan   OBJECT-TYPE
SYNTAX   INTEGER (0..255)
ACCESS   read-write
STATUS   mandatory
DESCRIPTION
"Indicates the requested metering plan number while the value of the rmcImplementCommandSource-object is 'manual' and the rmcRequestAction-object has a value of 'trafficResponsive'. This value shall not exceed the value of the rmcMaxNumMeterPlans-object.
<Unit> number
<Object Identifier> 1.3.6.1.4.1.1206.4.2.2.3.1.7.1.3"
REFERENCE
"See Clause A.3"
::={ rmcMeterCtrlEntry 3 }

--3.4.1.4.4	Manual Rate
rmcManualRate   OBJECT-TYPE
SYNTAX   INTEGER (0..65535)
ACCESS   read-write
STATUS   mandatory
DESCRIPTION
"Indicates the requested metering rate while the value of the rmcImplementCommandSource-object is 'manual' and the rmcRequestAction-object has a value of 'fixedRate'. 
This value shall be expressed in 1-vph increments. 
A suggested usable range is 120-1800.
<Unit> vehicles per hour
<Object Identifier> 1.3.6.1.4.1.1206.4.2.2.3.1.7.1.4"
REFERENCE
"See Clause A.3"
::={ rmcMeterCtrlEntry 4 }

--3.4.1.4.5	Manual Vehicles-Per-Green
rmcManualVehiclesPerGrn   OBJECT-TYPE
SYNTAX   INTEGER (0..255)
ACCESS   read-write
STATUS   mandatory
DESCRIPTION
"Indicates the requested number of vehicles to pass during the green and yellow intervals of one cycle while the value of the 
rmcImplementCommandSource-object is 'manual'. 
The values shall be expressed in 1-vehicle increments. 
The suggested usable range is 1 to 5 vehicles.
<Unit> number
<Object Identifier> 1.3.6.1.4.1.1206.4.2.2.3.1.7.1.5"
REFERENCE
"See Clause A.3"
::={ rmcMeterCtrlEntry 5 }

--3.4.1.4.6	Interconnect Action
rmcIntercoAction   OBJECT-TYPE
SYNTAX   INTEGER {
   dark (1),
   restInGreen (2),
   fixedRate (3),
   trafficResponsive (4),
   emergencyGreen (5),
   skip (6) }
ACCESS   read-write
STATUS   mandatory
DESCRIPTION 
"Indicates the requested action if the metered lane is commanded by 
interconnect. The values are:
dark - indicates that the metered lane will advance to the Pre-Metering Non-
    Green interval.
restInGreen - indicates that the metered lane will advance to  the Pre-
    Metering Green interval.
fixedRate - indicates that the metered lane will operate using the value of 
    the rmcIntercoRate-object.
trafficResponsive -indicates that the metered lane will operate using mainline 
    station traffic conditions and the value of the rmcIntercoPlan-object.
emergencyGreen - indicates that the metered lane will advance to and remain in 
    the Post-metering Green interval without entering the Shutdown Green, 
    Shutdown Yellow, Shutdown Red or Shutdown Warning intervals when the 
    metered lane is NOT in the Non-metering state. The metered lane will 
    advance to the Pre-Metering Green interval when the metered lane is in the 
    Non-metering state.
skip - indicates that the next-lower level command source shall be considered 
    as specified by the rmcCmdSourcePriorityOrder-object.
<Object Identifier> 1.3.6.1.4.1.1206.4.2.2.3.1.7.1.6"
REFERENCE
"See Clause A.3"
::={ rmcMeterCtrlEntry 6 }

--3.4.1.4.7	Interconnect Plan
rmcIntercoPlan   OBJECT-TYPE
SYNTAX   INTEGER (0..255)
ACCESS   read-write
STATUS   mandatory
DESCRIPTION
"Indicates the requested metering plan number if the metered lane is commanded by interconnect and the rmcRequestAction-object has a value of 'trafficResponsive'. This value shall not exceed the value of the rmcMaxNumMeterPlans-object.
<Unit> number
<Object Identifier> 1.3.6.1.4.1.1206.4.2.2.3.1.7.1.7"
REFERENCE
"See Clause A.3"
::={ rmcMeterCtrlEntry 7 }

--3.4.1.4.8	Interconnect Rate
rmcIntercoRate   OBJECT-TYPE
SYNTAX   INTEGER (0..65535)
ACCESS   read-write
STATUS   mandatory
DESCRIPTION
"Indicates the requested metering rate if the metered lane is commanded by interconnect and the rmcRequestAction-object has a value of 'fixedRate'.
This value shall be expressed in 1-vph increments. 
A suggested usable range is 120 to 1800. 
<Unit> vehicles per hour
<Object Identifier> 1.3.6.1.4.1.1206.4.2.2.3.1.7.1.8"
REFERENCE
"See Clause A.3"
::={ rmcMeterCtrlEntry 8 }

--3.4.1.4.9	Interconnect Vehicles-Per-Green
rmcIntercoVehiclesPerGrn   OBJECT-TYPE
SYNTAX   INTEGER (0..255)
ACCESS   read-write
STATUS   mandatory
DESCRIPTION
"Indicates the requested number of vehicles to pass during the green and yellow intervals of one cycle while the metered lane is commanded by interconnect (value of the rmcImplementCommandSource-object is 'interconnect').
This value shall be expressed in 1-vehicle increments. 
A suggested usable range is 1 to 5. 
<Unit> number
<Object Identifier> 1.3.6.1.4.1.1206.4.2.2.3.1.7.1.9"
REFERENCE
"See Clause A.3"
::={ rmcMeterCtrlEntry 9 }

--3.4.1.4.10	Communications Action Mode
rmcCommActionMode   OBJECT-TYPE
SYNTAX   INTEGER {
   dark (1),
   restInGreen (2),
   fixedRate (3),
   trafficResponsive (4),
   emergencyGreen (5),
   skip (6) }
ACCESS   read-write
STATUS   mandatory
DESCRIPTION 
"Indicates the commanded action from the TMC. When this object is set, the 
value of this object is copied into the rmcCommActionStatus object. The 
values are:
dark - indicates that the metered lane will advance to the Pre-Metering Non-
    Green interval.
restInGreen - indicates that the metered lane will advance to the Pre-Metering 
    Green interval.
fixedRate - indicates that the metered lane will operate using the value of 
    the rmcCommRate-object.
trafficResponsive -indicates that the metered lane will operate using mainline 
    station traffic conditions and the value of the rmcCommPlan-object.
emergencyGreen - indicates that the metered lane will advance to and remain in 
    the Post-metering Green interval without entering the Shutdown Green, 
    Shutdown Yellow, Shutdown Red or Shutdown Warning intervals when the 
    metered lane is NOT in the Non-metering state. The metered lane will 
    advance to the Pre-Metering Green interval when the metered lane is in the 
    Non-metering state.
skip - indicates that the next-lower level command source shall be considered
    as specified by the rmcCmdSourcePriorityOrder-object. 
<Object Identifier> 1.3.6.1.4.1.1206.4.2.2.3.1.7.1.10"
REFERENCE
"See Clause A.3"
::={ rmcMeterCtrlEntry 10 }
-- USERS TAKE NOTE OF MULTIPLE VERSIONS -
-- the name of the object was changed from 'rmcCommActionStatus' to
-- 'rmcCommActionMode'. This change does not cause any backwards 
-- compatibility problems. 

--3.4.1.4.11	Communications Plan
rmcCommPlan   OBJECT-TYPE
SYNTAX   INTEGER (0..255)
ACCESS   read-write
STATUS   mandatory
DESCRIPTION
"Indicates the requested metering plan number if the metered lane is commanded by communications and the rmcRequestAction-object has a value of 'trafficResponsive'. This value shall not exceed the value of the rmcMaxNumMeteringPlans-object. 
<Unit> number
<Object Identifier> 1.3.6.1.4.1.1206.4.2.2.3.1.7.1.11"
REFERENCE
"See Clause A.3"
::={ rmcMeterCtrlEntry 11 }

--3.4.1.4.12	Communications Rate
rmcCommRate   OBJECT-TYPE
SYNTAX   INTEGER (0..65535)
ACCESS   read-write
STATUS   mandatory
DESCRIPTION
"Indicates the requested metering rate in vehicles per hour (vph) if the metered lane is commanded by communications and the rmcRequestAction-object has a value of 'fixedRate'. 
This value shall be expressed in 1-vph increments. 
A suggested usable range is 120 to 1800. 
<Unit> vehicles per hour
<Object Identifier> 1.3.6.1.4.1.1206.4.2.2.3.1.7.1.12"
REFERENCE
"See Clause A.3"
::={ rmcMeterCtrlEntry 12 }

--3.4.1.4.13	Communications Vehicles-Per-Green
rmcCommVehiclesPerGrn   OBJECT-TYPE
SYNTAX   INTEGER (0..255)
ACCESS   read-write
STATUS   mandatory
DESCRIPTION
"Indicates the requested number of vehicles that are allowed to pass during the green and yellow intervals of one cycle while the metered lane is commanded by communications (value of the rmcImplementCommandSource-object is 'communications').
This value shall be expressed in 1-vehicle increments. 
A suggested usable range is 1 to 5. 
<Unit> number
<Object Identifier> 1.3.6.1.4.1.1206.4.2.2.3.1.7.1.13"
REFERENCE
"See Clause A.3"
::={ rmcMeterCtrlEntry 13 }

--3.4.1.4.14	Default Action
rmcDefaultAction   OBJECT-TYPE
SYNTAX   INTEGER {
   dark (1),
   restInGreen (2),
   fixedRate (3),
   trafficResponsive (4),
   emergencyGreen (5) }
ACCESS   read-write
STATUS   mandatory
DESCRIPTION 
"Indicates the requested action if the metered lane is commanded by default 
settings. The values are:
dark - indicates that the metered lane will advance to the Pre-Metering Non-
    Green interval.
restInGreen - indicates that the metered lane will advance to the Pre-Metering 
    Green interval.
fixedRate - indicates that the metered lane will operate using the value of 
    the rmcDefaultRate-object.
trafficResponsive -indicates that the metered lane will operate using mainline 
    station traffic conditions and the value of the rmcDefaultPlan-object.
emergencyGreen - indicates that the metered lane will advance to and remain in 
    the Post-metering Green interval without entering the Shutdown Green, 
    Shutdown Yellow, Shutdown Red or Shutdown Warning intervals when the 
    metered lane is NOT in the Non-metering state. The metered lane will 
    advance to the Pre-Metering Green interval when the metered lane is in 
    the Non-metering state. 
<Object Identifier> 1.3.6.1.4.1.1206.4.2.2.3.1.7.1.14"
REFERENCE
"See Clause A.3"
::={ rmcMeterCtrlEntry 14 }

--3.4.1.4.15	Default Plan
rmcDefaultPlan   OBJECT-TYPE
SYNTAX   INTEGER (0..255)
ACCESS   read-write
STATUS   mandatory
DESCRIPTION
"Indicates the requested metering plan number if the metered lane is commanded by default settings and the rmcRequestAction-object has a value of 'trafficResponsive'. This value shall not exceed the value of the rmcMaxNumMeteringPlans-object. 
<Unit> number
<Object Identifier> 1.3.6.1.4.1.1206.4.2.2.3.1.7.1.15"
REFERENCE
"See Clause A.3"
::={ rmcMeterCtrlEntry 15 }

--3.4.1.4.16	Default Rate
rmcDefaultRate   OBJECT-TYPE
SYNTAX   INTEGER (0..65535)
ACCESS   read-write
STATUS   mandatory
DESCRIPTION
"Indicates the requested metering rate if the metered lane is commanded by default settings and the rmcRequestAction-object has a value of 'fixedRate'. This value shall be expressed in 1-vph increments. 
A suggested usable range is 120 to 1800. 
<Unit> vehicles per hour
<Object Identifier> 1.3.6.1.4.1.1206.4.2.2.3.1.7.1.16"
REFERENCE
"See Clause A.3"
::={ rmcMeterCtrlEntry 16 }

--3.4.1.4.17	Default Vehicles-Per-Green
rmcDefaultVehiclesPerGrn   OBJECT-TYPE
SYNTAX   INTEGER (0..255)
ACCESS   read-write
STATUS   mandatory
DESCRIPTION
"Indicates the number of vehicles that are allowed to pass during the green and yellow intervals of one cycle while the metered lane is commanded by default settings (value of the rmcImplementCommandSource-object is 'default').
This value shall be expressed in 1- vehicle increments. 
A suggested usable range is 1 to 5.
<Unit> number
<Object Identifier> 1.3.6.1.4.1.1206.4.2.2.3.1.7.1.17"
REFERENCE
"See Clause A.3"
::={ rmcMeterCtrlEntry 17 }

--3.4.1.4.18	Demand Detector Mode
rmcDemandMode   OBJECT-TYPE
SYNTAX   INTEGER {
   recalled (1),
   enabledCall (2),
   enabledStop (3) }
ACCESS   read-write
STATUS   mandatory
DESCRIPTION
"Indicates the mode of the demand detector. 
recalled - indicates that the demand detector will constantly place a call even without a vehicle being present in its detection zone.
enabledCall - indicates that the demand detector is ready to detect, and shall constantly place a call when it has failed.
enabledStop - indicates that the demand detector is ready to detect, and shall exit the Metering state when it has failed. 
<Object Identifier> 1.3.6.1.4.1.1206.4.2.2.3.1.7.1.18"
REFERENCE
"See Clause A.2.2.1, A.8.3.1.4.1 and A.8.5.3.4.1"
::={ rmcMeterCtrlEntry 18 }

--3.4.1.4.19	Pre-metering Non-green Indication Mode
rmcPreMeterNonGreen   OBJECT-TYPE
SYNTAX   INTEGER {
   other (1),
   allDark (2),
   flashYellow (3)}
ACCESS   read-write
STATUS   mandatory
DESCRIPTION
"Indicates which signal indication(s) for the metered lane shall be ON during the Pre-metering Non-green interval. 
other - indicates that the red, yellow and green indications used are not defined in NTCIP 1207 v02. 
allDark - indicates that the red, yellow and green indications will be OFF.
flashYellow - indicates that the yellow indication will be flashed, and the red and green indications will be OFF. 
    Reference MUTCD 2003, revision 1, section 4D.11.
<Object Identifier> 1.3.6.1.4.1.1206.4.2.2.3.1.7.1.19"
REFERENCE
"See Clause A.2.2"
::={ rmcMeterCtrlEntry 19 }

--3.4.1.4.20	Critical Flow Rate Threshold
rmcCritFlowRateThresh   OBJECT-TYPE
SYNTAX   INTEGER (0..65535)
ACCESS   read-write
STATUS   mandatory
DESCRIPTION
"Indicates the critical flow rate threshold to be used to supercede queue adjustment during traffic-responsive metering. 
This value shall be expressed in 1-vph increments. 
A suggested usable range is 0, 1000 to 3600. 
A value of zero (0) indicates that this threshold shall NOT be used to supercede queue adjustment during traffic-responsive metering.
<Unit> vehicles per hour
<Object Identifier> 1.3.6.1.4.1.1206.4.2.3.1.7.1.20"
REFERENCE
"See Clause A.4.3"
::={ rmcMeterCtrlEntry 20 }

--3.4.1.4.21	Critical Occupancy Threshold
rmcCritOccupancyThresh   OBJECT-TYPE
SYNTAX   INTEGER (0..65535)
ACCESS   read-write
STATUS   mandatory
DESCRIPTION
"Indicates the critical occupancy threshold to be used to supercede queue adjustment during traffic-responsive metering. 
This value shall be expressed in 0.1-percent increments (i.e, 40 = 4.0 percent). 
A suggested usable range is 0 and 50 to 300. 
A value of zero (0) indicates that this threshold shall NOT be used to supercede queue adjustment during traffic-responsive metering.
<Unit> tenth of percent
<Object Identifier> 1.3.6.1.4.1.1206.4.2.3.1.7.1.21"
REFERENCE
"See Clause A.4.3"
::={ rmcMeterCtrlEntry 21 }

--3.4.1.4.22	Critical Speed Threshold for Queue Adjustment
rmcCriticalSpeedThreshold   OBJECT-TYPE
SYNTAX   INTEGER (0..255)
ACCESS   read-write
STATUS   mandatory
DESCRIPTION
"Indicates the critical speed threshold to be used to supercede queue adjustment during traffic-responsive metering. 
This value shall be expressed in 1-km/h increments. 
A suggested usable range is 0, 15 to 100. 
A value of zero (0) indicates that this threshold shall NOT be used to supercede queue adjustment during traffic-responsive metering.
<Unit> kilometer per hour
<Object Identifier> 1.3.6.1.4.1.1206.4.2.3.1.7.1.22"
REFERENCE
"See Clause A.4.3"
::={ rmcMeterCtrlEntry 22 }

--3.4.1.5	Metered Lane Status Table
rmcMeterStatTable   OBJECT-TYPE
SYNTAX   SEQUENCE OF RmcMeterStatEntry
ACCESS   not-accessible
STATUS   mandatory
DESCRIPTION 
"A table containing the status information for a metered lane. 
<Table Type> static
<Object Identifier> 1.3.6.1.4.1.1206.4.2.2.3.1.8"
::={ rmcMeterMain 8 }

rmcMeterStatEntry   OBJECT-TYPE
SYNTAX   RmcMeterStatEntry
ACCESS   not-accessible
STATUS   mandatory
DESCRIPTION 
"Status parameters of the metered lanes status table. This table is directly correlated to the Metered Lane Control Table, which means that the number of rows in this table is exactly the same as the number of rows in the Metered Lane Control Table (AUGMENT TABLE in SNMPv2 terminology). Table management can only take place through the Metered Lane Control Table, while this table provides status information for the associated metered lane. 
<Object Identifier> 1.3.6.1.4.1.1206.4.2.2.3.1.8.1"
INDEX { rmcMeterNumber }
::={ rmcMeterStatTable 1 }

RmcMeterStatEntry ::=SEQUENCE {
	rmcRequestCommandSource       INTEGER,
	rmcImplementCommandSource     INTEGER,
	rmcImplementAction            INTEGER,
	rmcImplementPlan              INTEGER,
	rmcImplementRate              INTEGER,
	rmcImplementVehiclesPerGrn    INTEGER,

	rmcRequestAction              INTEGER,
	rmcRequestPlan                INTEGER,
	rmcRequestRate                INTEGER,
	rmcRequestVehiclesPerGrn      INTEGER,

	rmcCommActionStatus           INTEGER, -- changed name only in version 2

	rmcBaseMeterRate              INTEGER,
	rmcActiveMeterRate            INTEGER,

	rmcTBActionStatus             INTEGER,
	rmcTBPlanStatus               INTEGER,
	rmcTBRateStatus               INTEGER,
	rmcTBVehiclesPerGrnStatus     INTEGER,

	rmcActiveInterval             INTEGER,

	rmcTBCMinMeterRateStatus      INTEGER,
	rmcTBCMaxMeterRateStatus      INTEGER,
	rmcOperMinMeterRateStatus     INTEGER, -- deprectated in version 2
	rmcOperMinMeterRateStatusV2   INTEGER, -- added in version 2
	rmcOperMaxMeterRateStatus     INTEGER, -- deprectated in version 2
	rmcOperMaxMeterRateStatusV2   INTEGER, -- added in version 2
	rmcDemandStatus               INTEGER,
	rmcHistDemandStatus           INTEGER, -- added in version 2
	rmcCycleCount                 INTEGER, -- added in Version 2
	rmcCumulQueAdjStat            INTEGER, -- added in version 2
	rmcMainQueueFlag              INTEGER -- added in version 2
	}

--3.4.1.5.1	Requested Metering Command Source
rmcRequestCommandSource   OBJECT-TYPE
SYNTAX   INTEGER {
   manual (1),
   communications (2),
   interconnect (3),
   timebaseControl (4),
   default (5)}
ACCESS   read-only
STATUS   mandatory
DESCRIPTION 
"Indicates the command source that requests control of this metered lane. The 
values are:
manual - the metered lane is requested to be controlled locally at the site. 
communications - the metered lane is requested to be controlled by the central system. This usually means that the entire RMC is controlled centrally. 
interconnect - the metered lane is requested to be controlled by an on-street master controller. 
timebaseControl - the metered lane is requested to be controlled using values as selected via the Timebase Control Action table.
default - indicates that the metered lane is requested to be controlled using default settings. 
<Object Identifier> 1.3.6.1.4.1.1206.4.2.2.3.1.8.1.1"
REFERENCE
"See Clause A.3"
::={ rmcMeterStatEntry 1 }

--3.4.1.5.2	Implemented Metering Command Source
rmcImplementCommandSource   OBJECT-TYPE
SYNTAX   INTEGER {
   manual (1),
   communications (2),
   interconnect (3),
   timebaseControl (4),
   default (5)}
ACCESS   read-only
STATUS   mandatory
DESCRIPTION 
"Indicates the command source that currently controls this metered lane. The 
values are:
manual - the metered lane is currently controlled locally at the site.
communications - the metered lane is currently controlled by the central system. This usually means that the entire RMC is controlled centrally. 
interconnect - the metered lane is currently controlled by an on-street master controller. 
timebaseControl - the metered lane is currently controlled using values as selected via the Timebase Control Action table.
default - indicates that the metered lane is currently controlled using default settings. 
<Object Identifier> 1.3.6.1.4.1.1206.4.2.2.3.1.8.1.2"
REFERENCE
"See Clause A.3"
::={ rmcMeterStatEntry 2 }

--3.4.1.5.3	Implemented Action
rmcImplementAction   OBJECT-TYPE
SYNTAX   INTEGER {
   dark (1),
   restInGreen (2),
   fixedRate (3),
   trafficResponsive (4),
   emergencyGreen (5),
   holdMeter (6),
   holdNonMeter (7),
   holdRestInGreen (8)}
ACCESS   read-only
STATUS   mandatory
DESCRIPTION 
"Indicates the action that is active for the metered lane. The values are:
dark - indicates that the metered lane will advance to the Pre-Metering 
    Non-Green interval.
restInGreen - indicates that the metered lane will advance to the Pre-Metering 
    Green interval.
fixedRate - indicates that the metered lane will operate using the value of 
   the rmcImplementRate-object.
trafficResponsive -indicates that the metered lane will operate using mainline 
    station traffic conditions and the value of the rmcImplementPlan-object.
emergencyGreen - indicates that the metered lane will advance to and remain in 
    the Post-metering Green interval without entering the Shutdown Green, 
    Shutdown Yellow, Shutdown Red or Shutdown Warning intervals when the 
    metered lane is NOT in the Non-metering state. The metered lane will 
    advance to the Pre-Metering Green interval when the metered lane is in the 
    Non-metering state.
holdMeter - indicates that the metered lane will remain in the metering state 
    regardless of the requested action (rmcRequestedAction-object) due to 
    restrictions such as minimum metering times.
holdNonMeter - indicates that the metered lane will remain in the non-metering 
    state regardless of the requested action (rmcRequestedAction-object) due 
    to restrictions such as minimum non-metering times.
holdRestInGreen -  indicates that the metered lane was forced into the 
    Pre-Metering Green interval because another lane within this Dependency 
    Group is NOT in the non-metering state. 
<Object Identifier> 1.3.6.1.4.1.1206.4.2.2.3.1.8.1.3"
REFERENCE
"See Clause A.3, A.5.1, A.5.2, A.6.1, A.6.2, A.6.3 and A.7.2"
::={ rmcMeterStatEntry 3 }

--3.4.1.5.4	Implemented Plan
rmcImplementPlan   OBJECT-TYPE
SYNTAX   INTEGER (0..255)
ACCESS   read-only
STATUS   mandatory
DESCRIPTION
"Indicates the metering plan number that is implemented if the rmcImplementAction-object has a value of 'trafficResponsive'. This value 
shall not exceed the value of the rmcMaxNumMeteringPlans-object nor that of the rmcNumMeterPlans-object. 
<Unit> number
<Object Identifier> 1.3.6.1.4.1.1206.4.2.2.3.1.8.1.4"
REFERENCE
"See Clause A.5.2 and A.7.2"
::={ rmcMeterStatEntry 4 }

--3.4.1.5.5	Implemented Rate
rmcImplementRate   OBJECT-TYPE
SYNTAX   INTEGER (0..65535)
ACCESS   read-only
STATUS   mandatory
DESCRIPTION
"Indicates the base metering rate if the rmcImplementAction-object has a 
value of 'fixedRate'. 
This value shall be expressed in 1-vph increments. 
<Unit> number
<Object Identifier> 1.3.6.1.4.1.1206.4.2.2.3.1.8.1.5"
::={ rmcMeterStatEntry 5 }

--3.4.1.5.6	Implemented Vehicles-Per-Green
rmcImplementVehiclesPerGrn   OBJECT-TYPE
SYNTAX   INTEGER (0..255)
ACCESS   read-only
STATUS   mandatory
DESCRIPTION
"Indicates the number of vehicles that are currently allowed to pass during 
the green and yellow intervals of one cycle.
This value shall be expressed in 1-vehicle increments. 
<Unit> vehicles per hour
<Object Identifier> 1.3.6.1.4.1.1206.4.2.2.3.1.8.1.6"
REFERENCE
"See Clause A.3, A.8.3.2.1 and A.8.5.1.1"
::={ rmcMeterStatEntry 6 }

--3.4.1.5.7	Requested Action
rmcRequestAction   OBJECT-TYPE
SYNTAX   INTEGER {
   dark (1),
   restInGreen (2),
   fixedRate (3),
   trafficResponsive (4),
   emergencyGreen (5) }
ACCESS   read-only
STATUS   mandatory
DESCRIPTION 
"Indicates the action that is requested for this metered lane. The values 
are:
dark - indicates that the metered lane is requested to advance to the 
    Pre-Metering Non-Green interval.
restInGreen - indicates that the metered lane is requested to advance to the 
    Pre-Metering Green interval.
fixedRate - indicates that the metered lane is requested to operate using the
    value of the rmcRequestRate-object.
trafficResponsive -indicates that the metered lane is requested to operate 
    using mainline station traffic conditions and the value of the 
    rmcRequestPlan-object.
emergencyGreen - indicates that the metered lane is requested to advance to 
    and remain in the Post-metering Green interval without entering the 
    Shutdown Green, Shutdown Yellow, Shutdown Red or Shutdown Warning 
    intervals when the metered lane is NOT in the Non-metering state. The 
    metered lane shall advance to the Pre-Metering Green interval when the 
    metered lane is in the Non-metering state. 
<Object Identifier> 1.3.6.1.4.1.1206.4.2.2.3.1.8.1.7"
REFERENCE
"See Clause A.3"
::={ rmcMeterStatEntry 7 }

--3.4.1.5.8	Requested Plan
rmcRequestPlan   OBJECT-TYPE
SYNTAX   INTEGER (0..255)
ACCESS   read-only
STATUS   mandatory
DESCRIPTION
"Indicates the metering plan number that is requested if the rmcRequestAction-object has a value of 'trafficResponsive'. This value shall not exceed the value of the rmcMaxNumMeterPlans-object. 
<Unit> number
<Object Identifier> 1.3.6.1.4.1.1206.4.2.2.3.1.8.1.8"
REFERENCE
"See Clause A.3"
::={ rmcMeterStatEntry 8 }

--3.4.1.5.9	Requested Rate
rmcRequestRate   OBJECT-TYPE
SYNTAX   INTEGER (0..65535)
ACCESS   read-only
STATUS   mandatory
DESCRIPTION
"Indicates the metering rate that is requested if the rmcRequestAction-object 
has a value of 'fixedRate'. 
This value shall be expressed in 1-vph increments. 
<Unit> vehicles per hour
<Object Identifier> 1.3.6.1.4.1.1206.4.2.2.3.1.8.1.9"
::={ rmcMeterStatEntry 9 }

--3.4.1.5.10	Requested Vehicles-Per-Green
rmcRequestVehiclesPerGrn   OBJECT-TYPE
SYNTAX   INTEGER (0..255)
ACCESS   read-only
STATUS   mandatory
DESCRIPTION
"Indicates the number of vehicles that has been requested to pass during the green and yellow intervals of one cycle. 
This value shall be expressed in 1-vehicle increments. 
<Unit> number
<Object Identifier> 1.3.6.1.4.1.1206.4.2.2.3.1.8.1.10"
REFERENCE
"See Clause A.3"
::={ rmcMeterStatEntry 10 }

--3.4.1.5.11	Communications Action Status
rmcCommActionStatus   OBJECT-TYPE
SYNTAX   INTEGER {
   dark (1),
   restInGreen (2),
   fixedRate (3),
   trafficResponsive (4),
   emergencyGreen (5),
   skip (6),
   noComm (7) }
ACCESS   read-only
STATUS   mandatory
DESCRIPTION 
"Indicates the requested action if the metered lane is commanded by 
communications. If the value of this object is NOT 'noComm', then the action 
is directly determined by the value of the rmcCommActionMode-object. The 
values are:
dark - indicates that the metered lane will advance to the Pre-Metering 
    Non-Green interval.
restInGreen - indicates that the metered lane will advance to the Pre-Metering
    Green interval.
fixedRate - indicates that the metered lane will operate using the value of
    the rmcCommRate-object.
trafficResponsive -indicates that the metered lane will operate using mainline
    station traffic conditions and the value of the rmcCommPlan-object.
emergencyGreen - indicates that the metered lane will advance to the 
    Post-metering Green interval without entering the Shutdown Green, 
    Shutdown Yellow, Shutdown Red or Shutdown Warning intervals when the
    metered lane is NOT in the Non-metering state. The metered lane will
    advance to the Pre-Metering Green interval when the metered lane is in
    the Non-metering state.
skip - indicates that the next-lower level command source shall be considered
    as specified by the rmcCmdSourcePriorityOrder-object.
noComm - indicates that communications to the device is lost (device timed
    out based on the value of the rmcCommRefreshThreshold-object); the
    action associated with this state is that the next-lower level command
    source shall be considered as specified by the 
    rmcCmdSourcePriorityOrder-object. 
<Object Identifier> 1.3.6.1.4.1.1206.4.2.2.3.1.8.1.11"
REFERENCE
"See Clause A.3"
::={ rmcMeterStatEntry 11 }
-- USERS TAKE NOTE OF MULTIPLE VERSIONS -
-- the object name was changed from 'rmcCommAction' to 
-- 'rmcCommActionStatus'. This should not cause any backwards 
-- compatibility problems.

--3.4.1.5.12	Base Metering Rate
rmcBaseMeterRate   OBJECT-TYPE
SYNTAX   INTEGER (0..65535)
ACCESS   read-only
STATUS   mandatory
DESCRIPTION
"Indicates the metering rate for this metered lane PRIOR to any RATE adjustments. 
This value shall be expressed in 1-vph increments. 
<Unit> vehicles per hour
<Object Identifier> 1.3.6.1.4.1.1206.4.2.2.3.1.8.1.12"
REFERENCE
"See Clause A.3"
::={ rmcMeterStatEntry 12 }

--3.4.1.5.13	Active Metering Rate
rmcActiveMeterRate   OBJECT-TYPE
SYNTAX   INTEGER (0..65535)
ACCESS   read-only
STATUS   mandatory
DESCRIPTION
"Indicates the metering rate for this metered lane AFTER all RATE adjustments.
This value shall be expressed in 1-vph increments. 
<Unit> vehicles per hour
<Object Identifier> 1.3.6.1.4.1.1206.4.2.2.3.1.8.1.13"
REFERENCE
"See Clause A.3"
::={ rmcMeterStatEntry 13 }

--3.4.1.5.14	Timebase Control Action Status
rmcTBActionStatus   OBJECT-TYPE
SYNTAX   INTEGER {
   dark (1),
   restInGreen (2),
   fixedRate (3),
   trafficResponsive (4),
   emergencyGreen (5),
   skip (6) }
ACCESS   read-only
STATUS   mandatory
DESCRIPTION 
"Indicates the action that may be active if the metered lane is controlled
 by timebase control. This object is used to indicate the status of the entry,
 while the rmcTBActionCtrl-object allows to control the entry. The values 
are:
dark - indicates that the metered lane will advance to the Pre-Metering
    Non-Green interval.
restInGreen - indicates that the metered lane will advance to the 
    Pre-Metering Green interval.
fixedRate - indicates that the metered lane will operate using the value
    of the rmcTBRateStatus-object.
trafficResponsive -indicates that the metered lane will operate using
    mainline station traffic conditions and the value of the
    rmcTBPlanStatus-object.
emergencyGreen - indicates that the metered lane will advance to the
    Post-metering Green interval without entering the Shutdown Green,
    Shutdown Yellow, Shutdown Red or Shutdown Warning intervals when the
    metered lane is NOT in the Non-metering state. The metered lane will
    advance to the Pre-Metering Green interval when the metered lane is
    in the Non-metering state.
skip - indicates that the next-lower level command source shall be considered
    as specified by the rmcCmdSourcePriorityOrder-object. 
<Object Identifier> 1.3.6.1.4.1.1206.4.2.2.3.1.8.1.14"
REFERENCE
"See Clause A.3.1"
::={ rmcMeterStatEntry 14 }

--3.4.1.5.15	Timebase Control Plan Status
rmcTBPlanStatus   OBJECT-TYPE
SYNTAX   INTEGER (0..255)
ACCESS   read-only
STATUS   mandatory
DESCRIPTION
"Indicates the requested metering plan number if the metered lane is commanded by timebase control and the rmcRequestedAction-object has a value of 'trafficResponsive'. This value cannot exceed the value of the rmcMaxNumMeterPlans-object. This object is used to indicate the status of the entry, while the rmcTBPlanCtrl-object allows control of the entry. 
<Unit> number
<Object Identifier> 1.3.6.1.4.1.1206.4.2.2.3.1.8.1.15"
REFERENCE
"See Clause A.3.1"
::={ rmcMeterStatEntry 15 }

--3.4.1.5.16	Timebase Control Rate Status
rmcTBRateStatus   OBJECT-TYPE
SYNTAX   INTEGER (0..65535)
ACCESS   read-only
STATUS   mandatory
DESCRIPTION
"Indicates the requested metering rate if the metered lane is commanded by timebase control and the rmcRequestAction-object has a value of 'fixedRate'. This object is used to indicate the status of the entry, while the rmcTBPlanCtrl-object allows control of the entry. 
This value shall be expressed in 1-vph increments. 
<Unit> vehicles per hour
<Object Identifier> 1.3.6.1.4.1.1206.4.2.2.3.1.8.1.16"
REFERENCE
"See Clause A.3.1"
::={ rmcMeterStatEntry 16 }

--3.4.1.5.17	Timebase Control Vehicles-Per-Green Status
rmcTBVehiclesPerGrnStatus   OBJECT-TYPE
SYNTAX   INTEGER (0..255)
ACCESS   read-only
STATUS   mandatory
DESCRIPTION
"Indicates the requested number of vehicles to pass during the green and yellow intervals of one cycle while the metered lane is commanded by timebase control. This object is used to indicate the status of the entry, while the rmcTBVehiclesPerGrnCtrl-object allows control of the entry. 
This value shall be expressed in 1-vph increments.
A suggested usable range is 1 to 5.
<Unit> number
<Object Identifier> 1.3.6.1.4.1.1206.4.2.2.3.1.8.1.17"
REFERENCE
"See Clause A.3.1"
::={ rmcMeterStatEntry 17 }

--3.4.1.5.18	Active Interval Status 
rmcActiveInterval   OBJECT-TYPE
SYNTAX   INTEGER {
   initialization (1),
   preMeteringNonGreen (2),
   preMeteringGreen (3),
   startupAlert (4),
   startupWarning (5),
   startupGreen (6),
   startupYellow (7),
   startupRed (8),
   red (9),
   green (10),
   yellow (11),
   shutdownGreen (12),
   shutdownYellow (13),
   shutdownRed (14),
   shutdownWarning (15),
   postMeteringGreen (16) }
ACCESS   read-only
STATUS   mandatory
DESCRIPTION 
"Indicates the interval in which the metered lane is currently running. See the State Diagram (Figure 3) as displayed in Section 1.4 and Annex A for further explanations of the different values. 
<Object Identifier> 1.3.6.1.4.1.1206.4.2.2.3.1.8.1.18"
REFERENCE
"See Clause A.2.2"
::={ rmcMeterStatEntry 18 }

--3.4.1.5.19	Timebase Control Minimum Metering Rate Status
rmcTBCMinMeterRateStatus   OBJECT-TYPE
SYNTAX   INTEGER (0..65535)
ACCESS   read-only
STATUS   mandatory
DESCRIPTION
"Indicates the operational minimum metering rate, in vph. This object is used to indicate the status of the entry, while the rmcTBCMinMeterRateCtrl-object allows control of the entry.
This value shall be expressed in 1-vph increments. 
A value of zero (0) indicates this parameter is not used. 
<Unit> vehicles per hour
<Object Identifier> 1.3.6.1.4.1.1206.4.2.2.3.1.8.1.19"
REFERENCE
"See Clause A.3.1"
::={ rmcMeterStatEntry 19 }

--3.4.1.5.20	Timebase Control Maximum Metering Rate Status
rmcTBCMaxMeterRateStatus   OBJECT-TYPE
SYNTAX   INTEGER (0..65535)
ACCESS   read-only
STATUS   mandatory
DESCRIPTION
"Indicates the operational maximum metering rate, in vph. This object is used to indicate the status of the entry, while the rmcTBCMaxMeterRateCtrl-object allows control of the entry.
This value shall be expressed in 1-vph increments. 
A value of zero (0) indicates this parameter is not used. 
The value, if non-zero, shall be greater than or equal to the value of the
rmcOperMinMeterRateStatus-object. 
<Unit> vehicles per hour
<Object Identifier> 1.3.6.1.4.1.1206.4.2.2.3.1.8.1.20"
REFERENCE
"See Clause A.3.1"
::={ rmcMeterStatEntry 20 }

--3.4.1.5.21	Operational Minimum Metering Rate
rmcOperMinMeterRateStatus   OBJECT-TYPE
SYNTAX   INTEGER (0..65535)
ACCESS   read-only
STATUS   deprecated
DESCRIPTION
"Indicates the operational minimum metering rate, in vph. This object indicates the minimum of the maximum metering rate objects 
(rmcAbsoluteMaxMeterRate, rmcSystemMaxMeterRate, rmcTBCMaxMeterRateStatus) that is currently active of this metered lane. 
<Unit> vehicles per hour
<Object Identifier> 1.3.6.1.4.1.1206.4.2.2.3.1.8.1.21"
REFERENCE
"See Clause A.2.2"
::={ rmcMeterStatEntry 21 }
-- this object was deprectated because its description is incorrect. Another
-- object with the same information but the correct description was created.

--3.4.1.5.22	Operational Minimum Metering Rate - Version 2
rmcOperMinMeterRateStatusV2   OBJECT-TYPE
SYNTAX   INTEGER (0..65535)
ACCESS   read-only
STATUS   mandatory
DESCRIPTION
"Indicates the operational minimum metering rate, in vph. The value of this object is the maximum value of the minimum metering rate objects (rmcAbsoluteMinMeterRate-object, rmcSystemMinMeterRate-object, rmcTBCMinMeterRateStatus-object) that is currently active for this metered lane. 
This value shall be expressed in 1-vph increments.
<Unit> vehicles per hour
<Object Identifier> 1.3.6.1.4.1.1206.4.2.2.3.1.8.1.26"
REFERENCE
"See Clause A.2.2"
::={ rmcMeterStatEntry 26 }
-- this object was created because the description of the original object was 
-- incorrect.

--3.4.1.5.23	Operational Maximum Metering Rate
rmcOperMaxMeterRateStatus   OBJECT-TYPE
SYNTAX   INTEGER (0..65535)
ACCESS   read-only
STATUS   deprecated
DESCRIPTION
"Indicates the operational maximum metering rate, in vph. This object indicates the maximum of the minimum metering rate objects 
(rmcAbsoluteMinMeterRate, rmcSystemMinMeterRate, rmcTBCMinMeterRateStatus) that is currently active of this metered lane. 
This value shall be expressed in 1-vph increments. 
<Unit> vehicles per hour
<Object Identifier> 1.3.6.1.4.1.1206.4.2.2.3.1.8.1.22"
REFERENCE
"See Clause A.2.2"
::={ rmcMeterStatEntry 22 }
-- this object was deprectated because its description is incorrect. Another
-- object with the same information but the correct description was created.

--3.4.1.5.24	Operational Maximum Metering Rate - Version 2
rmcOperMaxMeterRateStatusV2   OBJECT-TYPE
SYNTAX   INTEGER (0..65535)
ACCESS   read-only
STATUS   mandatory
DESCRIPTION
"Indicates the operational maximum metering rate, in vph. The value of this object is the minimum value of the maximum metering rate objects (rmcAbsoluteMaxMeterRate-object, rmcSystemMaxMeterRate-object, rmcTBCMaxMeterRateStatus-object) that is currently active for this metered lane. 
This value shall be expressed in 1-vph increments. 
<Unit> vehicles per hour
<Object Identifier> 1.3.6.1.4.1.1206.4.2.2.3.1.8.1.27"
REFERENCE
"See Clause A.2.2"
::={ rmcMeterStatEntry 27 }
-- this object was created because the description of the original object was 
-- incorrect.

--3.4.1.5.25	Demand Detector Status
rmcDemandStatus   OBJECT-TYPE
SYNTAX   INTEGER {
   recalled (1),
   working (2),
   otherError (3),
   erraticCount (4),
   maxPresence (5),
   noActivity (6),
   errorAtSensor (7),
   depNoActivity (8), -- added in version 2
   depMaxPresence (9) -- added in version 2
   }
ACCESS   read-only
STATUS   mandatory
DESCRIPTION
"Indicates the status of the demand detector. The values are:
recalled - indicates that the value of the rmcDemandMode-object is 'recalled'.
working - indicates that this detector has no error.
otherError - indicates an error not defined here. See Operator's manual.
erraticCount - indicates that the vehicle count for this detector has exceeded the value of its rmcDemandErraticCount-object.
maxPresence - indicates a continuous actuation for this detector that has exceeded the value of its rmcDemandMaxPresence-object.
noActivity - indicates a continuous non-actuation for this detector that has exceeded the value of its rmcDemandNoActivity-object.
errorAtSensor - indicates that the sensor for this detector has reported an error. See Operator's manual.
depNoActivity - indicates a continuous non-actuation for this detector, while a count of vehicles on the passage detector in the same metered lane that has exceeded the value of its rmcDemandDependNoActivity-object.
depMaxPresence - indicates a continuous actuation for this detector, while a continuous non-actuation of the passage detector in the same metered lane that has exceeded the value of its rmcDemandDependMaxPresence-object.

The test results expressed by values 2, 4, 5, 6, 7, 8, and 9 are only 
meaningful, when rmcDemandMode is NOT 'Recalled'.

<Object Identifier> 1.3.6.1.4.1.1206.4.2.2.3.1.8.1.23"
REFERENCE
"See Clause A.2.2.1, A.8.3.1.4.1 and A.8.5.3.4.1"
::={ rmcMeterStatEntry 23 }

--3.4.1.5.26	Historical Demand Detector Status
rmcHistDemandStatus  OBJECT-TYPE
SYNTAX   INTEGER (0..65535) -- BITMAP16
ACCESS   read-only
STATUS   mandatory
DESCRIPTION
"Indicates the cumulative status of the demand detector. Status values are 
indicated as follows:
<Format> 
Bit Number   Name             Description
Bit 15:    reserved.
Bit 14:    reserved.
Bit 13:    reserved.
Bit 12:    reserved.
Bit 11:    reserved.
Bit 10:    reserved. 
Bit 09:    reserved.
Bit 08:    Dependent Max Presence - the rmcDemandStatus-object has or had a
                             value of 'depMaxPresence' since reset.
Bit 07:    Dependent No activity - the rmcDemandStatus-object has or had a 
                             value of 'depNoActivity' since reset.
Bit 06:    Error at Sensor - the rmcDemandStatus-object has or had a value of
                             'errorAtSensor' since reset.
Bit 05:    No activity     - the rmcDemandStatus-object has or had a value of
                             'noActivity' since reset.
Bit 04:    Max presence    - the rmcDemandStatus-object has or had a value of
                             'maxPresence' since reset.
Bit 03:    Erratic count   - the rmcDemandStatus-object has or had a value
                             of 'erraticCount' since reset.
Bit 02:    Other error     - the rmcDemandStatus-object has or had a value
                             of 'otherError' since reset.
Bit 01:    Working         - the rmcDemandStatus-object has or had a value
                             of 'working' since reset.
Bit 00:    Disabled        - the rmcDemandStatus-object has or had a value
                             of 'disabled' since reset.

In the context of this object, 'reset' means either an initialization of the 
RMC or a successful SET of the rmcHistDetectorReset-object. When a 'reset' 
occurs, all bits shall be set to 0.

All reserved bits shall always be set to zero (0). A bad value error shall 
be returned, if a management application writes a one (1) to any of the 
reserved bits.

<Object Identifier> 1.3.6.1.4.1.1206.4.2.2.3.1.8.1.24"
REFERENCE
"See Clause A.2.2.1"
::={ rmcMeterStatEntry 24 }

--3.4.1.5.27	Cycle Count Parameter
rmcCycleCount   OBJECT-TYPE
SYNTAX   INTEGER (0..255)
ACCESS   read-only
STATUS   mandatory
DESCRIPTION
" Indicates the count of the number of green intervals in the most recently completed calculation interval. 
Counts are expressed as an integer value. 
The value of 255 shall be returned to represent a missing value. 
<Unit> number
<Object Identifier> 1.3.6.1.4.1.1206.4.2.2.3.1.8.1.25"
REFERENCE
"See Clause A.2.2"
::={ rmcMeterStatEntry 25 }

--3.4.1.5.28	Cumulative Queue Adjustment Status
rmcCumulQueAdjStat   OBJECT-TYPE
SYNTAX   INTEGER {
	none (1),
	adjust (2),
	override (3) }
ACCESS   read-only
STATUS   mandatory
DESCRIPTION
"Indicates whether queue adjustment is currenly being applied to the metering rate of the lane. 
none -     indicates that no queue adjustment is currently being applied. 
adjust -   indicates that queue adjustment is currently being applied. 
override - indicates that the queue adjustment is overridden for this lane.
<Object Identifier> 1.3.6.1.4.1.1206.4.2.2.3.1.8.1.28"
REFERENCE
"See Clause A.2.2.3"
::={ rmcMeterStatEntry 28 }

--3.4.1.5.29	Mainline versus Queue Flag
rmcMainQueueFlag   OBJECT-TYPE
SYNTAX   INTEGER (0..1)
ACCESS   read-only
STATUS   mandatory
DESCRIPTION
"Indicates whether mainline detector station traffic conditions supercede queue adjustment for the lane. 
0 = false - mainline traffic conditions do not supercede queue adjustment for the lane.
1 = true - mainline traffic conditions supercede queue adjustment for the lane.
<Object Identifier> 1.3.6.1.4.1.1206.4.2.2.3.1.8.1.29"
REFERENCE
"See Clause A.4.3"
::={ rmcMeterStatEntry 29 }

--3.4.2	Metered Lane Dependency Group Configuration, Control and Status Node
rmcDependGroup  OBJECT IDENTIFIER ::={ rmcMeter 2}

--3.4.2.1	Maximum Number of Dependency Groups
rmcMaxNumDependGroup   OBJECT-TYPE
SYNTAX   INTEGER (1..255)
ACCESS   read-only
STATUS   mandatory
DESCRIPTION 
"Indicates the maximum number of dependency groups that can be stored in the rmcDependGroupCtrlTable-object, and, by association, in all other dependency group tables. At least one dependency group shall be defined. 
<Unit> number
<Object Identifier> 1.3.6.1.4.1.1206.4.2.2.3.2.1"
REFERENCE
"See Clause A.2.3"
::={ rmcDependGroup 1 }
-- USERS TAKE NOTE OF MULTIPLE VERSIONS -
-- the ACCESS was changed to start from 'read-write' to 'read-only'. 
-- This is because number of dependency groups cannot be changed remotely as 
-- the description indicates. This was incorrect in Version 1.
-- This does not cause backwards compatibility problems.

--3.4.2.2	Number of Dependency Groups
rmcNumDependGroup   OBJECT-TYPE
SYNTAX   INTEGER (1..255)
ACCESS   read-only
STATUS   mandatory
DESCRIPTION 
"Indicates the actual number of dependency groups that are present in the rmcDependGroupCtrlTable-object, and, by association, in all other dependency group tables. This value shall not exceed the value of the rmcMaxNumDependGroup-object.
<Unit> number
<Object Identifier> 1.3.6.1.4.1.1206.4.2.2.3.2.2"
REFERENCE
"See Clause A.2.3"
::={ rmcDependGroup 2 }
-- USERS TAKE NOTE OF MULTIPLE VERSIONS -
-- the ACCESS was changed from 'read-write' to 'read-only'. 
-- This is because the number of dependency groups cannot be changed remotely 
-- as the description indicates. This was incorrect in Version 1.
-- This does not cause backwards compatibility problems.

--3.4.2.3	Dependency Group Configuration and Control Table
rmcDependGroupCtrlTable   OBJECT-TYPE
SYNTAX   SEQUENCE OF RmcDependGroupCtrlEntry
ACCESS   not-accessible
STATUS   mandatory
DESCRIPTION 
"A table containing the configuration and control information for a dependency group. 
<Table Type> static
<Object Identifier> 1.3.6.1.4.1.1206.4.2.2.3.2.3"
::={ rmcDependGroup 3 }

rmcDependGroupCtrlEntry   OBJECT-TYPE
SYNTAX   RmcDependGroupCtrlEntry
ACCESS   not-accessible
STATUS   mandatory
DESCRIPTION 
"Configuration and control parameters of the dependency group table. At least
one dependency group shall be defined. A particular row of this table can be
managed using the rmcDependGroupMode-object. 
There is a one-to-one relationship between the values of the
rmcDependGroupNumber-object within the rmcMeterCfgTable-object and the number
of rows within this table. Each different value represents one row of this
table.
<Object Identifier> 1.3.6.1.4.1.1206.4.2.2.3.2.3.1"
INDEX { rmcDependGroupNumber }
::={ rmcDependGroupCtrlTable 1 }

RmcDependGroupCtrlEntry ::=SEQUENCE {
	rmcDependGroupMode       INTEGER,
	rmcSignalServiceMode     INTEGER,
	rmcShutGapTime           INTEGER,
	rmcShutGapReductTime     INTEGER,
	rmcShutGapReductValue    INTEGER,
	rmcGreenOffset           INTEGER,
	rmcMinFractionalOffset   INTEGER,
	rmcPriorityLaneNum       INTEGER,
	rmcPriorityRedDelay      INTEGER,
	rmcMergeMode             INTEGER,
	rmcMergeGap              INTEGER,
	rmcMergeDelay            INTEGER,
	rmcQueueMergeFlag        INTEGER,
	rmcMergeErraticCount     INTEGER,
	rmcMergeMaxPresence      INTEGER,
	rmcMergeNoActivity       INTEGER,
	rmcMinMutexRed           INTEGER -- added in version 2
	}

--3.4.2.3.1	Dependency Group Mode
rmcDependGroupMode   OBJECT-TYPE
SYNTAX   INTEGER (0..1)
ACCESS   read-write
STATUS   mandatory
DESCRIPTION
"Indicates whether the associated dependency group is used.
0 = disabled - the dependency group is not used.
1 = enabled - the dependency group is used. 
<Object Identifier> 1.3.6.1.4.1.1206.4.2.2.3.2.3.1.1"
REFERENCE
"See Clause A.2.3"
::={ rmcDependGroupCtrlEntry 1 }

--3.4.2.3.2	Signal Service Mode
rmcSignalServiceMode   OBJECT-TYPE
SYNTAX   INTEGER {
   none (1),
   mutex (2),
   fixedOffset (3),
   fractionalOffset (4) }
ACCESS   read-write
STATUS   mandatory
DESCRIPTION
"Indicates the signal service mode associated with this dependency group. The
 values are:
none - there is no dependency between the lanes within this dependency group. 
mutex - one and only lane in the dependency group shall display (or
    indicate)green at any given time during the Metering state. 
fixedOffset - the start of the green interval for any lane will occur no
    sooner than indicated in the value of the rmcGreenOffset-object after the 
    start of a previous green interval for a lane in the same dependency 
    group.
fractionalOffset - the start of the green interval for any lane will occur no
    sooner than indicated in the value of the rmcRequestCycleLength-object 
    divided by the number of metered lanes in the dependency group, after the 
    start of a previous green interval for a lane in the same dependency
    group. 
<Object Identifier> 1.3.6.1.4.1.1206.4.2.2.3.2.3.1.2"
REFERENCE
"See Clause A.2.3.2, A.3, A.8.2.2, A.8.3.1.3, A.8.3.1.4.1, A.8.5.3.3,
 A.8.5.3.4.1, A.8.5.3.5 and A.8.6.3"
::={ rmcDependGroupCtrlEntry 2 }

--3.4.2.3.3	Shutdown Gap Time
rmcShutGapTime   OBJECT-TYPE
SYNTAX   INTEGER (0..255)
ACCESS   read-write
STATUS   mandatory
DESCRIPTION
"Indicates the length of time between successive actuations of demand 
detectors necessary to terminate the shutdown metering.
This value shall be expressed in 0.1-second increments (i.e, 40 = 4.0 seconds). 
A suggested usable range is 0 and 10 to 100.
A value of zero (0) shall make the termination of shutdown metering dependent only on the shutdown time. 
<Unit> tenth of second
<Object Identifier> 1.3.6.1.4.1.1206.4.2.2.3.2.3.1.3"
REFERENCE
"See Clause A.8.2.1 and A.8.5.3.5"
::={ rmcDependGroupCtrlEntry 3 }

--3.4.2.3.4	Shutdown Gap Reduction Time
rmcShutGapReductTime   OBJECT-TYPE
SYNTAX   INTEGER (0..255)
ACCESS   read-write
STATUS   mandatory
DESCRIPTION
"Indicates the amount of time between reduction iterations for the shutdown gap time.
This value shall be expressed in 0.1-second increments (i.e, 40 = 4.0 seconds). 
A suggested usable range is 10 to 200. 
<Unit> tenth of second
<Object Identifier> 1.3.6.1.4.1.1206.4.2.2.3.2.3.1.4"
REFERENCE
"See Clause A.8.5.3.5"
::={ rmcDependGroupCtrlEntry 4 }

--3.4.2.3.5	Shutdown Gap Reduction Value
rmcShutGapReductValue   OBJECT-TYPE
SYNTAX   INTEGER (0..255)
ACCESS   read-write
STATUS   mandatory
DESCRIPTION
"Indicates the amount of time that the shutdown gap time is reduced for each iteration.
This value shall be expressed in 0.1-seconds increments (i.e, 40 = 4.0 seconds). 
A suggested usable range is 10 to 100. 
A value of '0' shall inhibit shutdown gap time reduction.
<Unit> tenth of second
<Object Identifier> 1.3.6.1.4.1.1206.4.2.2.3.2.3.1.5"
REFERENCE
"See Clause A.8.5.3.5"
::={ rmcDependGroupCtrlEntry 5 }

--3.4.2.3.6	Green Offset Time
rmcGreenOffset   OBJECT-TYPE
SYNTAX   INTEGER (0..255)
ACCESS   read-write
STATUS   mandatory
DESCRIPTION
"Indicates the length of time between the beginning of successive green intervals for metered lanes that have the same value for the 
rmcDependGroupNumber-object (combined in the same dependency group) and a value of 'fixedOffset' for the rmcSignalServiceMode-object. 
This value shall be expressed in 0.1-second increments (i.e, 40 = 4.0 seconds). 
A suggested usable range is 5 to 100.
<Unit> tenth of second
<Object Identifier> 1.3.6.1.4.1.1206.4.2.2.3.2.3.1.6"
REFERENCE
"See Clause A.2.3.2, A.8.3.4.1 and A.8.5.3.4.1"
::={ rmcDependGroupCtrlEntry 6 }

--3.4.2.3.7	Minimum Fractional Offset Time
rmcMinFractionalOffset   OBJECT-TYPE
SYNTAX   INTEGER (0..255)
ACCESS   read-write
STATUS   mandatory
DESCRIPTION
"Indicates the minimum length of time between the beginning of successive green intervals for metered lanes that have the same value for the rmcDependGroupNumber-object (combined in the same dependency group) and a value of 'fractionalOffset' for the rmcSignalServiceMode-object. 
This value shall be expressed in 0.1-second increments(i.e, 40 = 4.0 seconds). 
A suggested usable range is 0 and 5 to 50. 
A value of zero (0) shall indicate that this parameter does not represent a constraint.
<Unit> tenth of second
<Object Identifier> 1.3.6.1.4.1.1206.4.2.2.3.2.3.1.7"
REFERENCE
"See Clause A.2.3.2, A.8.3.4.1 and A.8.5.3.4.1"
::={ rmcDependGroupCtrlEntry 7 }

--3.4.2.3.8	Priority Lane Number
rmcPriorityLaneNum   OBJECT-TYPE
SYNTAX   INTEGER (0..255)
ACCESS   read-write
STATUS   mandatory
DESCRIPTION
"Indicates which metered lane in the dependency group lane sequence shall be treated as a priority lane. The value shall not exceed the value of the rmcMaxNumMeterLanes-object. 
A value of zero (0) indicates the absence of a priority lane in this dependency group. 
<Unit> number
<Object Identifier> 1.3.6.1.4.1.1206.4.2.2.3.2.3.1.8"
REFERENCE
"See Clause A.2.3.2, A.8.3.1.3 and A.8.5.3.3"
::={ rmcDependGroupCtrlEntry 8 }

--3.4.2.3.9	Priority Lane Red Delay Time
rmcPriorityRedDelay   OBJECT-TYPE
SYNTAX   INTEGER (0..255)
ACCESS   read-write
STATUS   mandatory
DESCRIPTION
"Indicates the minimum length of the red interval for each metered lane in the dependency group (if is NOT marked as the priority lane), when the demand detector of the priority lane is actuated. The purpose of this object is to give a vehicle in the priority lane a headway of at least the time indicated in this object. For each actuation of the demand detector in the priority lane and each metered lane, the value of this object shall only apply once. 
This value shall be expressed in 0.1-second increments(i.e, 40 = 4.0 seconds). 
A suggested usable range is 0 to 50.
<Unit> tenth of second
<Object Identifier> 1.3.6.1.4.1.1206.4.2.2.3.2.3.1.9"
REFERENCE
"See Clause A.8.3.1.3 and A.8.5.3.3"
::={ rmcDependGroupCtrlEntry 9 }

--3.4.2.3.10	Merge Detector Mode
rmcMergeMode   OBJECT-TYPE
SYNTAX   INTEGER (0..1)
ACCESS   read-write
STATUS   mandatory
DESCRIPTION
"Indicates the mode of the merge detector . The values are:
0 = disabled - indicates that the merge detector does not exist for this dependency group.
1 = enabled - indicates that the merge detector is ready to detect for this dependency group. 
<Object Identifier> 1.3.6.1.4.1.1206.4.2.2.3.2.3.1.10"
REFERENCE
"See Clause A.2.3.1"
::={ rmcDependGroupCtrlEntry 10 }

--3.4.2.3.11	Merge Gap Time
rmcMergeGap   OBJECT-TYPE
SYNTAX   INTEGER (0..255)
ACCESS   read-write
STATUS   mandatory
DESCRIPTION
"Indicates the length of time between successive actuations of the merge detector necessary to terminate the merge override condition( value of the rmcMergeFlag-object is set to 'false'). 
This value shall be expressed in 0.1-second increments(i.e, 40 = 4.0 seconds). 
A suggested usable range is 0 to 255. 
A value of '0' shall force the Merge Override Flag to be 'False' while the merge detector is not actuated.
<Unit> tenth of second
<Object Identifier> 1.3.6.1.4.1.1206.4.2.2.3.2.3.1.11"
REFERENCE
"See Clause A.8.4.1"
::={ rmcDependGroupCtrlEntry 11 }

--3.4.2.3.12	Merge Delay Time
rmcMergeDelay   OBJECT-TYPE
SYNTAX   INTEGER (0..255)
ACCESS   read-write
STATUS   mandatory
DESCRIPTION
"Indicates the length of time for continuous presence on the merge detector necessary to identify the merge override condition. If presence is detected for a duration equal to or greater than indicated by the value of this object, the value of the rmcMergeFlag-object will be set to 'true', which will inhibit the termination of the red interval for all metered lanes in 
this dependency group. 
This value shall be expressed in 0.1-second increments(i.e, 40 = 4.0 seconds). 
A suggested usable range is 0 to 255. 
A value of '0' shall force the Merge Override Flag to be 'False' while the merge detector is actuated.
<Unit> tenth of second
<Object Identifier> 1.3.6.1.4.1.1206.4.2.2.3.2.3.1.12"
REFERENCE
"See Clause A.8.4.1"
::={ rmcDependGroupCtrlEntry 12 }

--3.4.2.3.13	Queue versus Merge Flag
rmcQueueMergeFlag   OBJECT-TYPE
SYNTAX   INTEGER (0..1)
ACCESS   read-write
STATUS   mandatory
DESCRIPTION
"Indicates if queue override adjustments are given priority over merge 
override adjustment.
0 = false - merge override adjustment is given priority over queue override adjustments.
1 = true - queue override adjustments are given priority over merge override adjustment. 
<Object Identifier> 1.3.6.1.4.1.1206.4.2.2.3.2.3.1.13"
REFERENCE
"See Clause A.8.3.1.4.1, A.8.3.1.4.2, A.8.4.1, A.8.5.3.4.1 and A.8.5.3.4.2"
::={ rmcDependGroupCtrlEntry 13 }

--3.4.2.3.14	Merge Detector Erratic Count Threshold
rmcMergeErraticCount   OBJECT-TYPE
SYNTAX   INTEGER (0..255)
ACCESS   read-write
STATUS   mandatory
DESCRIPTION 
"If the vehicle count, over the most recently completed calculation interval, on the merge detector for a metered lane exceeds this
threshold, the rmcMergeStatus-object shall be set to a value of 'erraticCount'. 
This value shall be expressed in 1-vehicle increments. 
A suggested usable range is 0 to 30. 
A value of zero (0) shall inhibit the erratic count testing.
<Unit> number
<Object Identifier> 1.3.6.1.4.1.1206.4.2.2.3.2.3.1.14"
REFERENCE
"See Clause A.2.3.1"
::={ rmcDependGroupCtrlEntry 14 }

--3.4.2.3.15	Merge Detector Maximum Presence Threshold
rmcMergeMaxPresence   OBJECT-TYPE
SYNTAX   INTEGER (0..65535)
ACCESS   read-write
STATUS   mandatory
DESCRIPTION 
"If the input on the merge detector for this metered lane has been continuously actuated for longer than the time indicated by this threshold, the rmcMergeStatus-object shall be set to a value of 'maxPresence'. 
This value shall be expressed in 1-minute increments. 
A suggested usable range is 0 to 1500.
A value of zero (0) shall inhibit the maximum presence testing. 
<Unit> minute
<Object Identifier> 1.3.6.1.4.1.1206.4.2.2.3.2.3.1.15"
REFERENCE
"See Clause A.2.3.1"
::={ rmcDependGroupCtrlEntry 15 }

--3.4.2.3.16	Merge Detector No Activity Threshold
rmcMergeNoActivity   OBJECT-TYPE
SYNTAX   INTEGER (0..65535)
ACCESS   read-write
STATUS   mandatory
DESCRIPTION 
"If the input on the merge detector for this metered lane has not been actuated for longer than the time indicated by this threshold, the rmcMergeStatus-object shall be set to a value of 'noActivity'. 
This value shall be expressed in 1-minute increments. 
A suggested usable range is 0 to 1500. 
A value of zero (0) shall inhibit the no activity testing.
<Unit> minute
<Object Identifier> 1.3.6.1.4.1.1206.4.2.2.3.2.3.1.16"
REFERENCE
"See Clause A.2.3.1"
::={ rmcDependGroupCtrlEntry 16 }

--3.4.2.3.17	Minimum Mutex Red Time
rmcMinMutexRed   OBJECT-TYPE
SYNTAX   INTEGER (0..255)
ACCESS   read-write
STATUS   mandatory
DESCRIPTION
"Indicates the minimum amount of time that all metered lanes in the dependency group shall simultaneously remain in the Red or Shutdown Red intervals. 
This value shall be expressed in 0.1-second increments (i.e, 40 = 4.0 seconds). 
A suggested usable range is 10 to 100. 
A value of '0' shall indicate that no minimum simultaneous red time is 
required.
<Unit> tenth of second
<Object Identifier> 1.3.6.1.4.1.1206.4.2.2.3.2.3.1.17"
REFERENCE
"See Clause A.8.3.1.4.1, A.8.5.3.4"
::={ rmcDependGroupCtrlEntry 17 }

--3.4.2.4	Dependency Group Status Table
rmcDependGroupStatTable   OBJECT-TYPE
SYNTAX   SEQUENCE OF RmcDependGroupStatEntry
ACCESS   not-accessible
STATUS   mandatory
DESCRIPTION 
"A table containing the status information for a dependency group.
<Table Type> static
<Object Identifier> 1.3.6.1.4.1.1206.4.2.2.3.2.4"
::={ rmcDependGroup 4 }

rmcDependGroupStatEntry   OBJECT-TYPE
SYNTAX   RmcDependGroupStatEntry
ACCESS   not-accessible
STATUS   mandatory
DESCRIPTION 
"Status information of the dependency group table. This table is directly correlated to the Dependency Group Configuration and Control Table, which means that the number of rows in this table is exactly the same as the number of rows in the Dependency Group Configuration and Control Table (AUGMENT TABLE in SNMPv2 terminology). Table management can only take place through the Dependency Group Configuration and Control Table, while this table provides status information for the associated dependency group. 
<Object Identifier> 1.3.6.1.4.1.1206.4.2.2.3.2.4.1"
INDEX { rmcDependGroupNumber }
::={ rmcDependGroupStatTable 1 }

RmcDependGroupStatEntry ::=SEQUENCE {
	rmcMergeFlag         INTEGER,
	rmcMergeStatus       INTEGER,
	rmcHistMergeStatus   INTEGER, -- added in version 2
	rmcMergeOverStat    INTEGER   -- added in version 2
	}

--3.4.2.4.1	Merge Override Flag
rmcMergeFlag   OBJECT-TYPE
SYNTAX   INTEGER (0..1)
ACCESS   read-only
STATUS   mandatory
DESCRIPTION
"Indicates whether merge override conditions exist. 
0 = false - indicates that no merge override conditions exist.
1 = true - indicates that merge override conditions exist.
<Object Identifier> 1.3.6.1.4.1.1206.4.2.2.3.2.4.1.1"
REFERENCE
"See Clause A.2.2.1, A.2.2.3, A.2.3.1, A.8.3.1.4.1, A.8.3.1.4.2, A.8.4.1, A.8.5.3.4.1 and A.8.5.3.4.2"
::={ rmcDependGroupStatEntry 1 }

--3.4.2.4.2	Merge Detector Status
rmcMergeStatus   OBJECT-TYPE
SYNTAX   INTEGER {
   disabled (1),
   working (2),
   otherError (3),
   erraticCount (4),
   maxPresence (5),
   noActivity (6),
   errorAtSensor (7) }
ACCESS   read-only
STATUS   mandatory
DESCRIPTION
"Indicates the status of the merge detector. The values are: 
disabled - indicates that this detector is not used.
working - indicates that this detector has no error.
otherError - indicates an error not defined here. See Operator's manual.
erraticCount - indicates that the vehicle count for this detector has exceeded the value of its rmcMergeErraticCount-object.
maxPresence - indicates a continuous actuation for this detector that has exceeded the value of its rmcMergeMaxPresence-object.
noActivity - indicates a continuous non-actuation for this detector that has exceeded the value of its rmcMergeNoActivity-object. 
errorAtSensor - indicates that the sensor for this detector has reported an error. See Operator's manual. 
<Object Identifier> 1.3.6.1.4.1.1206.4.2.2.3.2.4.1.2" 
REFERENCE
"See Clause A.2.3.1"
::={ rmcDependGroupStatEntry 2 }

--3.4.2.4.3	Historical Merge Detector Status
rmcHistMergeStatus  OBJECT-TYPE
SYNTAX   INTEGER (0..65535) -- BITMAP16
ACCESS   read-only
STATUS   mandatory
DESCRIPTION
"Indicates the cumulative status of the merge detector. Status values are 
indicated as follows:
<Format> 
Bit Number    Name       Description
Bit 15:     reserved.
Bit 14:     reserved.
Bit 13:     reserved.
Bit 12:     reserved.
Bit 11:     reserved.
Bit 10:     reserved.
Bit 09:     reserved.
Bit 08:     reserved.
Bit 07:     reserved.
Bit 06:     Error at Sensor - the rmcMergeStatus-object has or had
                          a value of 'Disabled' since reset.
Bit 05:     No activity - the rmcMergeStatus-object has or had
                          a value of 'noActivity' since reset.
Bit 04:     Max presence - the rmcMergeStatus-object has or had
                          a value of 'maxPresence' since reset.
Bit 03:     Erratic count - the rmcMergeStatus-object has or had
                          a value of 'erraticCount' since reset.
Bit 02:     Other error - the rmcMergeStatus-object has or had
                          a value of 'otherError' since reset.
Bit 01:     Working     - the rmcMergeStatus-object has or had
                          a value of 'Working' since reset.
Bit 00:     Disabled    - the rmcMergeStatus-object has or had
                          a value of 'Disabled' since reset.

In the context of this object, 'reset' means either an initialization of the 
RMC or a successful SET of the rmcHistDetectorReset-object. When a 'reset' 
occurs, all bits shall be set to 0.

All reserved bits shall always be set to zero (0). A bad value error shall 
be returned, if a management application writes a one (1) to any of the 
reserved bits.

<Object Identifier> 1.3.6.1.4.1.1206.4.2.2.3.2.4.1.3"
REFERENCE
"See Clause A.2.3.1"
::={ rmcDependGroupStatEntry 3 }

--3.4.2.4.4	Merge Override Status
rmcMergeOverStat   OBJECT-TYPE
SYNTAX   INTEGER (0..1)
ACCESS   read-only
STATUS   mandatory
DESCRIPTION
"Indicates whether the rmcMergeFlag-object has or had a value of 'True' in the most recently completed calculation interval. 
0 = false - indicates that the rmcMergeFlag-object does not have and did not have a value of 'True' in the most recently completed 		calculation interval.
1 = true - indicates that the rmcMergeFlag-object has or had a value of 'True' in the most recently completed calculation interval.
<Object Identifier> 1.3.6.1.4.1.1206.4.2.2.3.2.4.1.4"
REFERENCE
"See Clause A.2.3.1"
::={ rmcDependGroupStatEntry 4 }

--3.4.3	Queue Detector Configuration, Control and Status Node
rmcQueue  OBJECT IDENTIFIER ::={ rmcMeter 3 }

-- This node is an identifier used to group the objects for the configuration,
-- control and status of the queue detectors parameters that are common to all
-- ramp meter devices.

--3.4.3.1	Maximum Number of Queue Detectors
rmcMaxNumQueueEntries   OBJECT-TYPE
SYNTAX   INTEGER (1..255)
ACCESS   read-only
STATUS   mandatory
DESCRIPTION 
"Indicates the maximum number of queue detectors that can be stored in the Queue Detector Configuration and Control Table, and, by association, in the queue detector status tables. 
<Unit> number
<Object Identifier> 1.3.6.1.4.1.1206.4.2.2.3.3.1"
REFERENCE
"See Clause A.2.2.3"
::={ rmcQueue 1 }
-- USERS TAKE NOTE OF MULTIPLE VERSIONS -
-- the INTEGER range was changed to start at 1 instead of 0. This
-- does not cause backwards compatibility problems because this object would
-- not have been supported, if the function was not supported in the device.

--3.4.3.2	Number of Queue Detectors
rmcNumQueueEntries   OBJECT-TYPE
SYNTAX   INTEGER (1..255)
ACCESS   read-only
STATUS   mandatory
DESCRIPTION 
"Indicates the actual number of queue detectors that are present in the Queue
Detector Configuration and Control Table, and, by association, in the queue
detector status tables. 
This value shall not exceed the value of the rmcMaxNumQueueEntries-object.
<Unit> number
<Object Identifier> 1.3.6.1.4.1.1206.4.2.2.3.3.2"
REFERENCE
"See Clause A.2.2.3"
::={ rmcQueue 2 }
-- USERS TAKE NOTE OF MULTIPLE VERSIONS -
-- the INTEGER range was changed to start at 1 instead of 0. This
-- does not cause backwards compatibility problems because this object would
-- not have been supported, if the function was not supported in the device.

--3.4.3.3	Queue Detector Configuration and Control Table
rmcQueueCtrlTable   OBJECT-TYPE
SYNTAX   SEQUENCE OF RmcQueueCtrlEntry
ACCESS   not-accessible
STATUS   mandatory
DESCRIPTION 
"A table containing the queue detectors that can be selected based on the
metered lane number. 
<Table Type> static
<Object Identifier> 1.3.6.1.4.1.1206.4.2.2.3.3.3"
::={ rmcQueue 3 }

rmcQueueCtrlEntry   OBJECT-TYPE
SYNTAX RmcQueueCtrlEntry
ACCESS   not-accessible
STATUS   mandatory
DESCRIPTION 
"Configuration and control parameters of the queue detector table. The entry with the lower index value will be considered the highest priority queue detector.
A particular row of this table can be managed using the rmcQueueDetectMode-object. If that object has a value of 'disabled', the associated row is not used.
<Object Identifier> 1.3.6.1.4.1.1206.4.2.2.3.3.3.1"
INDEX { rmcMeterNumber, rmcQueueNum }
::={ rmcQueueCtrlTable 1 }


RmcQueueCtrlEntry ::=SEQUENCE {
	rmcQueueNum                 INTEGER,
	rmcQueueType                INTEGER,
	rmcQueueDetectMode          INTEGER,

	rmcQueueLengthUpLimit       INTEGER,
	rmcQueueLengthLowLimit      INTEGER,

	rmcQueueOccUpLimit          INTEGER,
	rmcQueueOccUpDelay          INTEGER,
	rmcQueueOccLowLimit         INTEGER,
	rmcQueueOccLowDelay         INTEGER,

	rmcQueueQOccUpLimit         INTEGER,
	rmcQueueQOccUpDelay         INTEGER,
	rmcQueueQOccLowLimit        INTEGER,
	rmcQueueQOccLowDelay        INTEGER,

	rmcQueueAdjustMode          INTEGER,
	rmcQueueAdjustRate          INTEGER,
	rmcQueueAdjustRateLimit     INTEGER,
	rmcQueueAdjustRateDelay     INTEGER,
	rmcQueueAdjustRateIter      INTEGER,

	rmcQueueAdjustLevel         INTEGER,
	rmcQueueAdjustLevelLimit    INTEGER,
	rmcQueueAdjustLevelDelay    INTEGER,
	rmcQueueAdjustLevelIter     INTEGER,

	rmcQueueReplaceRate         INTEGER,

	rmcQueueErraticCount        INTEGER,
	rmcQueueMaxPresence         INTEGER,
	rmcQueueNoActivity          INTEGER,
	rmcQueueDependMaxPresence   INTEGER, -- added in version 2
	rmcQueueDependNoActivity    INTEGER  -- added in version 2
	}

--3.4.3.3.1	Queue Detector Number
rmcQueueNum   OBJECT-TYPE
SYNTAX   INTEGER (1..255)
ACCESS   read-only
STATUS   mandatory
DESCRIPTION
"Indicates the secondary index into the table. The value of this object serves as a unique identifier for every queue detector, regardless of the value of the rmcQueueType-object, that is associated with the metered lane 
described in the primary key. 
The value of this secondary key object cannot exceed the value of the rmcMaxNumQueueEntries-object.
<Object Identifier> 1.3.6.1.4.1.1206.4.2.2.3.3.3.1.1"
REFERENCE
"See Clause A.2.2.3"
::={ rmcQueueCtrlEntry 1 }

--3.4.3.3.2	Queue Type
rmcQueueType   OBJECT-TYPE
SYNTAX   INTEGER {
   other (1),
   intermediate (2),
   excessive (3) }
ACCESS   read-write
STATUS   mandatory
DESCRIPTION
"Indicates whether the queue detector is an intermediate or excessive. The
values are:
other - other queue detector type than specified below. See Operator's Manual.
intermediate - indicates that this detector is an intermediate queue detector. 
excessive - indicates that this detector is an excessive queue detector. 
<Object Identifier> 1.3.6.1.4.1.1206.4.2.2.3.3.3.1.2"
REFERENCE
"See Clause A.2.2.3 and A.9.2"
::={ rmcQueueCtrlEntry 2 }

--3.4.3.3.3	Queue Detection Mode
rmcQueueDetectMode   OBJECT-TYPE
SYNTAX   INTEGER {
   disabled (1),
   count (2),
   occupancy (3),
   quickOccupancy (4) }
ACCESS   read-write
STATUS   mandatory
DESCRIPTION
"Indicates the mode that is being used to determine the existence of a queue.
The values are:
disabled - no queue detection shall occur.
count - the existence of a queue shall be determined using the difference
    between vehicle counts on the queue and passage detectors. ANNEX A 
    describes in detail how a queue can be determined using 'counts'. 
occupancy - the existence of a queue shall be determined using the occupancy
    measured at the queue detector over the number of calculation intervals 
    as specified in the rmcQueueOccUpDelay and rmcQueueOccLowDelay objects. 
    ANNEX A describes in detail how an queue can be determined using 
    'occupancy'. 
quickOccupancy -- the existence of an  queue shall be determined using the 
    occupancy measured at the queue detector over the period of time as 
    specified in the rmcQueueQOccUpDelay and rmcQueueQOccLowDelay objects. 
    ANNEX A describes in detail how a queue can be determined using 
    'quickOccupancy'. 
<Object Identifier> 1.3.6.1.4.1.1206.4.2.2.3.3.3.1.3"
REFERENCE
"See Clause A.9.1"
::={ rmcQueueCtrlEntry 3 }

--3.4.3.3.4	Queue Length Upper Limit
rmcQueueLengthUpLimit   OBJECT-TYPE
SYNTAX   INTEGER (0..255)
ACCESS   read-write
STATUS   mandatory
DESCRIPTION
"Indicates the number of vehicles stored on the metered lane that, if exceeded, defines the existence of a queue if the rmcQueueDetectMode-object has a value of 'count'. This count is obtained by summing the differences between the vehicle counts at the passage and queue detectors over successive calculation intervals. 
This value shall be greater than or equal to the value of the rmcQueueLengthLowLimit-object.
This value shall be expressed in 1-vehicle increments. 
A suggested usable range is 5 to 100. 
<Unit> number
<Object Identifier> 1.3.6.1.4.1.1206.4.2.2.3.3.3.1.4"
REFERENCE
"See Clause A.9.1"
::={ rmcQueueCtrlEntry 4 }

--3.4.3.3.5	Queue Length Lower Limit
rmcQueueLengthLowLimit   OBJECT-TYPE
SYNTAX   INTEGER (0..255)
ACCESS   read-write
STATUS   mandatory
DESCRIPTION
"Indicates the number of vehicles stored on the metered lane that, if not exceeded, defines the non-existence of a queue if the rmcQueueDetectMode-object has a value of 'count'. This count is obtained by summing the differences between the vehicle counts at the passage and queue detectors over successive calculation intervals intervals. 
This value shall be less than or equal to the value of the rmcQueueLengthUpLimit-object. 
This value shall be expressed in 1-vehicle increments. 
A suggested usable range is 5 to 100.
<Unit> number
<Object Identifier> 1.3.6.1.4.1.1206.4.2.2.3.3.3.1.5"
REFERENCE
"See Clause A.9.1"
::={ rmcQueueCtrlEntry 5 }

--3.4.3.3.6	Queue Occupancy Upper Limit
rmcQueueOccUpLimit   OBJECT-TYPE
SYNTAX   INTEGER (0..65535)
ACCESS   read-write
STATUS   mandatory
DESCRIPTION
"Indicates the occupancy of a queue detector that, if exceeded, defines the existence of an queue when the rmcQueueDetectMode-object has a value of 'occupancy'. 
This value shall be greater than or equal to the value of the 
rmcQueueOccLowLimit-object. 
This value shall be expressed in 0.1-percent increments(i.e, 40 = 4.0 percent). 
A suggested usable range is 0 to 1000.
<Unit> tenth of percent
<Object Identifier> 1.3.6.1.4.1.1206.4.2.2.3.3.3.1.6"
REFERENCE
"See Clause A.9.1"
::={ rmcQueueCtrlEntry 6 }

--3.4.3.3.7	Queue Occupancy Upper Delay
rmcQueueOccUpDelay   OBJECT-TYPE
SYNTAX   INTEGER (0..255)
ACCESS   read-write
STATUS   mandatory
DESCRIPTION
"Indicates the number of calculation intervalsthat the occupancy of the queue detector shall exceed the value of the rmcQueueOccUpLimit-object to define the existence of a queue, if the rmcQueueDetectMode-object has a value of
'occupancy'. 
This value shall be greater than or equal to the value of the rmcQueueOccLowDelay-object.
This value shall be expressed in 1-interval increments. 
A suggested usable range is 0 to 30. 
<Unit> interval
<Object Identifier> 1.3.6.1.4.1.1206.4.2.2.3.3.3.1.7"
REFERENCE
"See Clause A.9.1"
::={ rmcQueueCtrlEntry 7 }

--3.4.3.3.8	Queue Occupancy Lower Limit
rmcQueueOccLowLimit   OBJECT-TYPE
SYNTAX   INTEGER (0..65535)
ACCESS   read-write
STATUS   mandatory
DESCRIPTION
"Indicates the occupancy of a queue detector that, when not exceeded, defines the non-existence of a queue if the rmcQueueDetectMode-object has a value of 'occupancy'. 
This value shall be less than or equal to the value of the rmcQueueOccUpLimit-object.
This value shall be expressed in 0.1-percent increments (i.e, 40 = 4.0 percent). 
A suggested usable range is 0 to 1000. 
<Unit> tenth of percent
<Object Identifier> 1.3.6.1.4.1.1206.4.2.2.3.3.3.1.8"
REFERENCE
"See Clause A.9.1"
::={ rmcQueueCtrlEntry 8 }

--3.4.3.3.9	Queue Occupancy Lower Delay
rmcQueueOccLowDelay   OBJECT-TYPE
SYNTAX   INTEGER (0..255)
ACCESS   read-write
STATUS   mandatory
DESCRIPTION
"Indicates the number of calculation intervalsthat the occupancy of the queue detector does not exceed the value of the rmcQueueOccLowLimit-object to define the non-existence of a queue if the rmcQueueDetectMode-object has a value of 'occupancy'. 
This value shall be less than or equal to the value of the rmcQueueOccUpDelay-object.
This value shall be expressed in 1-interval increments. 
A suggested usable range is 0 to 30. 
<Unit> interval
<Object Identifier> 1.3.6.1.4.1.1206.4.2.2.3.3.3.1.9"
REFERENCE
"See Clause A.9.1"
::={ rmcQueueCtrlEntry 9 }

--3.4.3.3.10	Queue Quick Occupancy Upper Limit
rmcQueueQOccUpLimit   OBJECT-TYPE
SYNTAX   INTEGER (0..65535)
ACCESS   read-write
STATUS   mandatory
DESCRIPTION
"Indicates the occupancy of a queue detector that, if exceeded, defines the existence of an queue if the rmcQueueDetectMode-object has a value of 'quickOccupancy'. 
This value shall be greater than or equal to the value of the rmcQueueQOccLowLimit-object.
This value shall be expressed in 0.1-percent increments (i.e, 40 = 4.0 percent). 
A suggested usable range is 0 to 1000. 
<Unit> tenth of percent
<Object Identifier> 1.3.6.1.4.1.1206.4.2.2.3.3.3.1.10"
REFERENCE
"See Clause A.9.1"
::={ rmcQueueCtrlEntry 10 }

--3.4.3.3.11	Queue Quick Occupancy Upper Delay
rmcQueueQOccUpDelay   OBJECT-TYPE
SYNTAX   INTEGER (0..65535)
ACCESS   read-write
STATUS   mandatory
DESCRIPTION
"Indicates the length of time that the occupancy of the queue detector exceeds the value of the rmcQueueOccUpLimit-object to define the existence of a queue, if the rmcQueueDetectMode-object has a value of 'quickOccupancy'. 
This value shall be greater than or equal to the value of the rmcQueueQOccLowDelay-object.
This value shall be expressed in 0.1-second increments (i.e, 40 = 4.0 seconds). 
A suggested usable range is 0 to 300. 
<Unit> tenth of second
<Object Identifier> 1.3.6.1.4.1.1206.4.2.2.3.3.3.1.11"
REFERENCE
"See Clause A.9.1"
::={ rmcQueueCtrlEntry 11 }

--3.4.3.3.12	Queue Quick Occupancy Lower Limit
rmcQueueQOccLowLimit   OBJECT-TYPE
SYNTAX   INTEGER (0..65535)
ACCESS   read-write
STATUS   mandatory
DESCRIPTION
"Indicates the occupancy of a queue detector that, when not exceeded, defines the non-existence of a queue if the rmcQueueDetectMode-object has a value of 'quickOccupancy'. 
This value shall be less than or equal to the value of the rmcQueueQOccUpLimit-object.
This value shall be expressed in 0.1-percent increments (i.e, 40 = 4.0 percent). 
A suggested usable range is 0 to 1000. 
<Unit> tenth of percent
<Object Identifier> 1.3.6.1.4.1.1206.4.2.2.3.3.3.1.12"
REFERENCE
"See Clause A.9.1"
::={ rmcQueueCtrlEntry 12 }

--3.4.3.3.13	Queue Quick Occupancy Lower Delay
rmcQueueQOccLowDelay   OBJECT-TYPE
SYNTAX   INTEGER (0..65535)
ACCESS   read-write
STATUS   mandatory
DESCRIPTION
"Indicates the length of time that the occupancy of the queue detector does not exceed the value of the rmcQueueOccLowLimit-object to define the non-existence of a queue, if the rmcQueueDetectMode-object has a value of 'quickOccupancy'. 
This value shall be less than or equal to the value of the rmcQueueQOccUpDelay-object.
This value shall be expressed in 0.1-second increments (i.e, 40 = 4.0 seconds). 
A suggested usable range is 0 to 300. 
<Unit> tenth of second
<Object Identifier> 1.3.6.1.4.1.1206.4.2.2.3.3.3.1.13"
REFERENCE
"See Clause A.9.1"
::={ rmcQueueCtrlEntry 13 }

--3.4.3.3.14	Queue Adjustment Mode
rmcQueueAdjustMode   OBJECT-TYPE
SYNTAX   INTEGER {
   other (1),
   rate (2),
   level (3),
   fixed (4) }
ACCESS   read-write
STATUS   mandatory
DESCRIPTION
"Indicates the process used to override the queue. The values are:
other - other source of control than specified below. See Operator's manual;
rate - the queue will be overridden by increasing the current metering rate. 
    For details, see ANNEX A.
level - the queue will be overriden by decreasing the current metering level.
    This mode shall only be usable while the rmcImplementAction-object has a 
    value of 'trafficResponsive'. For details, see ANNEX A.
fixed - the queue will be overriden by replacing the current metering rate 
    with the rate indicated in the rmcQueueReplaceRate-object. For details,
    see ANNEX A. 
<Object Identifier> 1.3.6.1.4.1.1206.4.2.2.3.3.3.1.14"
REFERENCE
"See Clause A.9.2"
::={ rmcQueueCtrlEntry 14 }

--3.4.3.3.15	Queue Adjustment Rate
rmcQueueAdjustRate   OBJECT-TYPE
SYNTAX   INTEGER (0..65535)
ACCESS   read-write
STATUS   mandatory
DESCRIPTION
"Indicates the rate by which the current metering rate will be increased if a queue has been detected AND the rmcQueueAdjustMode-object has a value of 'rate'.
This value shall be expressed in 1-vph increments. 
A suggested usable range is 0, 5 to 1800. 
A value of zero (0) indicates that no adjustments are made to the current metering rate. 
<Unit> vehicles per hour
<Object Identifier> 1.3.6.1.4.1.1206.4.2.2.3.3.3.1.15"
REFERENCE
"See Clause A.9.2"
::={ rmcQueueCtrlEntry 15 }

--3.4.3.3.16	Queue Adjustment Rate Limit
rmcQueueAdjustRateLimit   OBJECT-TYPE
SYNTAX   INTEGER (0..65535)
ACCESS   read-write
STATUS   mandatory
DESCRIPTION
"Indicates the highest metering rate at which the metered lane will be metered if a queue has been detected AND the rmcQueueAdjustMode-object has a value of 'rate'.
This value shall be expressed in 1-vehicle increments. 
A suggested usable range is 0, 120 to 1800. 
A value of zero (0) indicates this parameter shall not be used. 
<Unit> number
<Object Identifier> 1.3.6.1.4.1.1206.4.2.2.3.3.3.1.16"
REFERENCE
"See Clause A.9.2"
::={ rmcQueueCtrlEntry 16 }

--3.4.3.3.17	Queue Adjustment Rate Delay Time
rmcQueueAdjustRateDelay   OBJECT-TYPE
SYNTAX   INTEGER (0..255)
ACCESS   read-write
STATUS   mandatory
DESCRIPTION
"Indicates the length of time between successive queue override rate adjustments.
This value shall be expressed in 1-second increments. 
A suggested usable range is 20 to 240. 
<Unit> second
<Object Identifier> 1.3.6.1.4.1.1206.4.2.2.3.3.3.1.17"
REFERENCE
"See Clause A.9.2"
::={ rmcQueueCtrlEntry 17 }

--3.4.3.3.18	Queue Adjustment Rate Iterations
rmcQueueAdjustRateIter   OBJECT-TYPE
SYNTAX   INTEGER (0..255)
ACCESS   read-write
STATUS   mandatory
DESCRIPTION
"Indicates the maximum number of queue override rate adjustments which can be made during the existence of a single queue. 
A suggested usable range is either 
- 0, or
- 1 to 20 iterations in 1-iteration increments for queue detectors whose rmcQueueType-object has a value of 'intermediate', or 
- 1 iteration for queue detectors whose rmcQueueType-object has a value of 'excessive'. 
A value of zero (0) indicates that the current metering rate is not increased after a queue has been detected. 
<Object Identifier> 1.3.6.1.4.1.1206.4.2.2.3.3.3.1.18"
REFERENCE
"See Clause A.9.2"
::={ rmcQueueCtrlEntry 18 }

--3.4.3.3.19	Queue Adjustment Level
rmcQueueAdjustLevel   OBJECT-TYPE
SYNTAX   INTEGER (0..255)
ACCESS   read-write
STATUS   mandatory
DESCRIPTION
"Indicates the number of levels by which the current metering level will be decreased if a queue has been detected AND the rmcQueueAdjustMode-object has a value of 'level'.
This value shall be expressed in 1-level increments. 
A suggested usable range is 0, 1 to 5. 
A value of zero (0) indicates that no adjustments are made to the current metering level. 
<Unit> number
<Object Identifier> 1.3.6.1.4.1.1206.4.2.2.3.3.3.1.19"
REFERENCE
"See Clause A.9.2"
::={ rmcQueueCtrlEntry 19 }

--3.4.3.3.20	Queue Adjustment Level Limit
rmcQueueAdjustLevelLimit   OBJECT-TYPE
SYNTAX   INTEGER (0..255)
ACCESS   read-write
STATUS   mandatory
DESCRIPTION
"Indicates the lowest metering level at which the metered lane shall be metered if a queue has been detected AND the rmcQueueAdjustMode-object has a value of 'level'.
This value shall be expressed in 1-level increments. 
A suggested usable range is 0, 1 to 5. 
A value of zero (0) indicates this parameter shall not be used. 
<Unit> number
<Object Identifier> 1.3.6.1.4.1.1206.4.2.2.3.3.3.1.20"
REFERENCE
"See Clause A.9.2"
::={ rmcQueueCtrlEntry 20 }

--3.4.3.3.21	Queue Adjustment Level Delay Time
rmcQueueAdjustLevelDelay   OBJECT-TYPE
SYNTAX   INTEGER (0..255)
ACCESS   read-write
STATUS   mandatory
DESCRIPTION
"Indicates the length of time between successive queue override level adjustments.
This value shall be expressed in 1-second increments. 
A suggested usable range is 20 to 240. 
<Unit> second
<Object Identifier> 1.3.6.1.4.1.1206.4.2.2.3.3.3.1.21"
REFERENCE
"See Clause A.9.2"
::={ rmcQueueCtrlEntry 21 }

--3.4.3.3.22	Queue Adjustment Level Iterations
rmcQueueAdjustLevelIter   OBJECT-TYPE
SYNTAX   INTEGER (0..255)
ACCESS   read-write
STATUS   mandatory
DESCRIPTION
"Indicates the maximum number of queue override level adjustments which can be  made during the existence of a single queue.
A suggested usable range is either
- 0, or
- 1 to 5 iterations in 1-iteration increments for queue detectors whose 
    rmcQueueType-object has a value of 'intermediate', or
- 1 iteration for queue detectors whose rmcQueueType-object has a value of 
    'excessive'. 
A value of zero (0) indicates that the current metering level is not decreased after a queue has been detected. 
<Object Identifier> 1.3.6.1.4.1.1206.4.2.2.3.3.3.1.22"
REFERENCE
"See Clause A.9.2"
::={ rmcQueueCtrlEntry 22 }

--3.4.3.3.23	Queue Replacement Rate
rmcQueueReplaceRate   OBJECT-TYPE
SYNTAX   INTEGER (0..65535)
ACCESS   read-write
STATUS   mandatory
DESCRIPTION
"Indicates the metering rate at which the metered lane will be metered if a queue has been detected AND the rmcQueueAdjustMode-object has a value of 'fixed'. 
This value shall be expressed in 1-vehicle increments. 
A suggested usable range is 0, 600 to 1800. 
A value of zero (0) indicates that no adjustments to the metering rate are made when the rmcQueueAdjustMode-object has a value of 'fixed'.
<Unit> number
<Object Identifier> 1.3.6.1.4.1.1206.4.2.2.3.3.3.1.23"
REFERENCE
"See Clause A.9.2"
::={ rmcQueueCtrlEntry 23 }

--3.4.3.3.24	Queue Detector Erratic Count Threshold
rmcQueueErraticCount   OBJECT-TYPE
SYNTAX   INTEGER (0..255)
ACCESS   read-write
STATUS   mandatory
DESCRIPTION 
"If the vehicle count, over the most recently completed calculation interval, on a queue detector exceeds this threshold, the rmcQueueStatus-object for that detector shall be set to 'erraticCount'. 
This value shall be expressed in 1-vehicle increments. 
A suggested usable range is 0, 2 to 10. 
A value of zero (0) shall inhibit the erratic count testing on this 
queue detector.
<Unit> number
<Object Identifier> 1.3.6.1.4.1.1206.4.2.2.3.3.3.1.24"
REFERENCE
"See Clause A.2.2.3"
::={ rmcQueueCtrlEntry 24 }

--3.4.3.3.25	Queue Detector Maximum Presence Threshold
rmcQueueMaxPresence   OBJECT-TYPE
SYNTAX   INTEGER (0..65535)
ACCESS   read-write
STATUS   mandatory
DESCRIPTION 
"If the input on a queue detector has been continuously actuated for longer than the time indicated by this threshold, the rmcQueueStatus-object shall be set to 'maxPresence' for that detector. 
This value shall be expressed in 1-minute increments. 
A suggested usable range is 0 to 1500.
A value of zero (0) shall inhibit the maximum presence testing on this queue detector.
<Unit> minute
<Object Identifier> 1.3.6.1.4.1.1206.4.2.2.3.3.3.1.25"
REFERENCE
"See Clause A.2.2.3"
::={ rmcQueueCtrlEntry 25 }

--3.4.3.3.26	Queue Detector No Activity Threshold
rmcQueueNoActivity   OBJECT-TYPE
SYNTAX   INTEGER (0..65535)
ACCESS   read-write
STATUS   mandatory
DESCRIPTION 
"If the input on a queue detector has not been actuated for longer than the time indicated by this threshold, the rmcQueueStatus-object shall be set to 'noActivity' for that detector. 
This value shall be expressed in 1-minute increments. 
A suggested usable range is 0 to 1500.
A value of zero (0) shall inhibit the no activity testing on this queue detector.
<Unit> minute
<Object Identifier> 1.3.6.1.4.1.1206.4.2.2.3.3.3.1.26"
REFERENCE
"See Clause A.2.2.3"
::={ rmcQueueCtrlEntry 26 }

--3.4.3.3.27	Queue Detector Dependent Maximum Presence Threshold
rmcQueueDependMaxPresence   OBJECT-TYPE
SYNTAX   INTEGER (0..65535)
ACCESS   read-write
STATUS   mandatory
DESCRIPTION 
"If the input on the queue detector for a metered lane has been continuously actuated, while the input on the passage detector for the same metered lane has been continuously non-actuated for longer than the time indicated by this threshold and the rmcPassageMode-object is not 'recalled' and the rmcPassageStatus-object is 'working', the rmcQueueStatus-object for that metered lane shall be set to a value of 'depMaxPresence'. 
This value shall be expressed in 1-second increments. 
A suggested usable range is 0 to 600. 
A value of zero (0) shall inhibit the dependent maximum presence testing.
<Unit> second
<Object Identifier> 1.3.6.1.4.1.1206.4.2.2.3.3.3.1.27"
REFERENCE
"See Clause A.2.2.3"
::={ rmcQueueCtrlEntry 27 }

--3.4.3.3.28	Queue Detector Dependent No Activity Threshold
rmcQueueDependNoActivity   OBJECT-TYPE
SYNTAX   INTEGER (0..255)
ACCESS   read-write
STATUS   mandatory
DESCRIPTION 
"If the input on the queue detector for a metered lane has not been actuated, while more vehicles than indicated by this threshold have been counted on the passage detector of the same metered lane and the rmcPassageMode-object is not 'recalled' and the rmcPassageStatus-object is 'working', the rmcQueueStstus-object for that metered lane shall be set to a value of 'depNoActivity'. 
This value shall be expressed in 1-vehicle increments. 
A suggested usable range is 0 to 30. 
A value of zero (0) shall inhibit the dependent no activity testing.
<Unit> number
<Object Identifier> 1.3.6.1.4.1.1206.4.2.2.3.3.3.1.28"
REFERENCE
"See Clause A.2.2.3"
::={ rmcQueueCtrlEntry 28 }

--3.4.3.4	Queue Detector Status Table
rmcQueueStatTable   OBJECT-TYPE
SYNTAX   SEQUENCE OF RmcQueueStatEntry
ACCESS   not-accessible
STATUS   mandatory
DESCRIPTION 
"A table containing the status information for queue detectors. 
<Table Type> static
<Object Identifier> 1.3.6.1.4.1.1206.4.2.2.3.3.3.10"
::={ rmcQueue 10 }
--Editor's Note: There is a skip in OID at this point, but this was already in
--version 1 and I cannot change the OID in version 2 for any existing object.

rmcQueueStatEntry   OBJECT-TYPE
SYNTAX RmcQueueStatEntry
ACCESS   not-accessible
STATUS   mandatory
DESCRIPTION 
"Status parameters of the queue detector table. The entry with the lower index value will be considered the higher priority queue detector. This table is directly correlated to the Queue Detector Configuration and Control Table, which means that the number of rows in this table is exactly the same as the number of rows in the Queue Detector Configuration and Control Table (AUGMENT
TABLE in SNMPv2 terminology). Table management can only take place through the Queue Detector Configuration and Control Table, while this table provides status information for the associated queue detector. 
<Object Identifier> 1.3.6.1.4.1.1206.4.2.2.3.3.3.10.1"
INDEX { rmcMeterNumber, rmcQueueNum }
::={ rmcQueueStatTable 1 }

RmcQueueStatEntry ::=SEQUENCE {
	rmcQueueFlag        INTEGER,
	rmcQueueStatus      INTEGER,
	rmcHistQueueStatus  INTEGER -- added in version 2
	}

--3.4.3.4.1	Queue Detected Flag
rmcQueueFlag   OBJECT-TYPE
SYNTAX   INTEGER (0..1)
ACCESS   read-only
STATUS   mandatory
DESCRIPTION
"Indicates whether a queue has been detected
0 = false - indicates that no queue has been detected. 
1 = true - indicates that a queue has been detected. 

<Object Identifier> 1.3.6.1.4.1.1206.4.2.2.3.3.3.10.1.1"
REFERENCE
"See Clause A.6, A.8.3.1.2, A.8.4.1, A.8.5.3.5, A.9.1 and A.9.2"
::={ rmcQueueStatEntry 1 }

--3.4.3.4.2	Queue Detector Status
rmcQueueStatus   OBJECT-TYPE
SYNTAX   INTEGER {
   disabled (1),
   working (2),
   otherError (3),
   erraticCount (4),
   maxPresence (5),
   noActitity (6),
   errorAtSensor (7),
   noDepActivity (8), -- added in version 2
   maxDepPresence (9) -- added in version 2
   }
ACCESS   read-only
STATUS   mandatory
DESCRIPTION
"Indicates the status of the queue detector. The values are:
disabled - indicates that this detector is not used.
working - indicates that this detector has no error.
otherError - indicates an error not defined here. See Operator's manual;
erraticCount - indicates that the vehicle count for this detector has exceeded the value of its rmcQueueErraticCount-object;
maxPresence - indicates that a continuous actuation for this detector has exceeded the value of its rmcQueueMaxPresence-object;
noActivity - indicates that a continuous non-actuation for this detector has exceeded the value of its rmcQueueNoActivity-object;
errorAtSensor - indicates that the sensor for this detector has reported an error. See Operator's manual.
depNoActivity - indicates a continuous non-actuation for this detector, while a count of vehicles on the passage detector in the same metered lane that has exceeded the value of its rmcQueueDepNoActivity-object.
depMaxPresence - indicates a continuous actuation for this detector, while a continuous non-actuation of the passage detector in the same metered lane that has exceeded the value of its rmcQueueDepMaxPresence-object.

<Object Identifier> 1.3.6.1.4.1.1206.4.2.2.3.3.3.10.1.2"
REFERENCE
"See Clause A.2.2.3"
::={ rmcQueueStatEntry 2 }

--3.4.3.4.3	Historical Queue Detector Status
rmcHistQueueStatus  OBJECT-TYPE
SYNTAX   INTEGER (0..65535) -- BITMAP16
ACCESS   read-only
STATUS   mandatory
DESCRIPTION
"Indicates the cumulative status of the queue detector. The values are: 
<Format> 
Bit Number   Name        Description
Bit 15:     reserved.
Bit 14:     reserved.
Bit 13:     reserved.
Bit 12:     reserved.
Bit 11:     reserved.
Bit 10:     reserved. 
Bit 09:     reserved.
Bit 08:     Dependent Max Presence - the rmcQueueStatus-object has or had
                         a value of 'depNoActivity' since reset.
Bit 07:     Dependent No Activity - the rmcQueueStatus-object has or had
                         a value of 'depNoActivity' since reset.
Bit 06:     Error At Sensor - the rmcQueueStatus-object has or had
                         a value of 'Disabled' since reset.
Bit 05:     No Activity  - the rmcQueueStatus-object has or had
                         a value of 'noActivity' since reset.
Bit 04:     Max Presence - the rmcQueueStatus-object has or had
                         a value of 'maxPresence' since reset.
Bit 03:     Erratic Count - the rmcQueueStatus-object has or had
                         a value of 'erraticCount' since reset.
Bit 02:     Other Error - the rmcQueueStatus-object has or had
                         a value of 'otherError' since reset.
Bit 01:     Working     - the rmcQueueStatus-object has or had
                         a value of 'Working' since reset.
Bit 00:     Disabled    - the rmcQueueStatus-object has or had
                          a value of 'Disabled' since reset.

In the context of this object, 'reset' means either an initialization of the 
RMC or a successful SET of the rmcHistDetectorReset-object. When a 'reset' 
occurs, all bits shall be set to 0.

All reserved bits shall always be set to zero (0). A bad value error shall 
be returned, if a management application writes a one (1) to any of the 
reserved bits.

<Object Identifier> 1.3.6.1.4.1.1206.4.2.2.3.3.3.10.1.3"
REFERENCE
"See Clause A.2.2.3"
::={ rmcQueueStatEntry 3 }

--3.4.4	Metered Lane Passage Detector Configuration, Control and Status Node
rmcPassage  OBJECT IDENTIFIER ::= { rmcMeter 5 }

-- This node is an identifier used to group the objects for the configuration, 
-- control and status of the passage detectors parameters that are common to 
-- all ramp meter control units.

--3.4.4.1	Passage Detector Configuration and Control Table
rmcPassageCtrlTable   OBJECT-TYPE
SYNTAX   SEQUENCE OF RmcPassageCtrlEntry
ACCESS   not-accessible
STATUS   mandatory
DESCRIPTION 
"A table containing the configuration and control information for a passage detector. 
<Table Type> static
<Object Identifier> 1.3.6.1.4.1.1206.4.2.2.3.5.1"
::={ rmcPassage 1 }

rmcPassageCtrlEntry   OBJECT-TYPE
SYNTAX   RmcPassageCtrlEntry
ACCESS   not-accessible
STATUS   mandatory
DESCRIPTION 
"Configuration and control parameters of the passage detector table. The number of rows within this table shall be the same as within the Metered Lane Configuration Table. If this table is supported, there shall be a passage detector for each metered lane. 
The rows within this table cannot be managed following the same principles applied to other tables. It is anticipated that, if passage detectors are utilized within an implementation, each metered lane will have one passage detector. However, not every metered lane might have a physical passage detector and shall therefore be set into 'recalled' using the rmcPassageMode-object to utilize the passage detection functionality.
<Object Identifier> 1.3.6.1.4.1.1206.4.2.2.3.5.1.1"
INDEX { rmcMeterNumber }
::={ rmcPassageCtrlTable 1 }

RmcPassageCtrlEntry ::=SEQUENCE {
	rmcPassageMode              INTEGER,
	rmcPassageErraticCount      INTEGER,
	rmcPassageMaxPresence       INTEGER,
	rmcPassageNoActivity        INTEGER,
	rmcPassageDependNoActivity  INTEGER -- added in version 2
	}

--3.4.4.1.1	Passage Detector Mode
rmcPassageMode   OBJECT-TYPE
SYNTAX   INTEGER {
   recalled (1),
   enabledCall (2),
   enabledNoCall (3) }
ACCESS   read-write
STATUS   mandatory
DESCRIPTION
"Indicates the mode of the passage detector. The values are: 
recalled - indicates that the passage detector shall constantly place a call, even without a vehicle being present in its detection zone.
enabledCall - indicates that the passage detector is ready to detect, and shall constantly place a call when it has failed.
enabledNoCall - indicates that the passage detector is ready to detect, and shall NOT place a call when it has failed. 
<Object Identifier> 1.3.6.1.4.1.1206.4.2.2.3.5.1.1.1"
REFERENCE
"See Clause A.2.2.2"
::={ rmcPassageCtrlEntry 1 }

--3.4.4.1.2	Passage Detector Erratic Count Threshold
rmcPassageErraticCount   OBJECT-TYPE
SYNTAX   INTEGER (0..255)
ACCESS   read-write
STATUS   mandatory
DESCRIPTION 
"If the vehicle count, over the most recently completed calculation interval, on the passage detector for this metered lane exceeds this
threshold, the rmcPassageStatus-object shall be set to a value of 'erraticCount'. 
This value shall be expressed in 1-vehicle increments. 
A suggested usable range is 0, 5 to 10. 
A value of zero (0) shall inhibit the erratic count testing.
<Unit> number
<Object Identifier> 1.3.6.1.4.1.1206.4.2.2.3.5.1.1.2"
REFERENCE
"See Clause A.2.2.2"
::={ rmcPassageCtrlEntry 2 }

--3.4.4.1.3	Passage Detector Maximum Presence Threshold
rmcPassageMaxPresence   OBJECT-TYPE
SYNTAX   INTEGER (0..65535)
ACCESS   read-write
STATUS   mandatory
DESCRIPTION 
"If the input on the passage detector for this metered lane has been continuously actuated for longer than the time indicated by this threshold, the rmcPassageStatus-object shall be set to a value of 'maxPresence'. 
This value shall be expressed in 1-minute increments. 
A suggested usable range is 0 to 1500. 
A value of zero (0) shall inhibit the maximum presence testing.
<Unit> minute
<Object Identifier> 1.3.6.1.4.1.1206.4.2.2.3.5.1.1.3"
REFERENCE
"See Clause A.2.2.2"
::={ rmcPassageCtrlEntry 3 }

--3.4.4.1.4	Passage Detector No Activity Threshold
rmcPassageNoActivity   OBJECT-TYPE
SYNTAX   INTEGER (0..65535)
ACCESS   read-write
STATUS   mandatory
DESCRIPTION 
"If the input on the passage detector for this metered lane has not been actuated for longer than the time indicated by this threshold, the rmcPassageStatus-object shall be set to a value of 'noActivity'. 
This value shall be expressed in 1-minute increments. 
A suggested usable range is 0 to 1500. 
A value of zero (0) shall inhibit the no activity testing.
<Unit> minute
<Object Identifier> 1.3.6.1.4.1.1206.4.2.2.3.5.1.1.4"
REFERENCE
"See Clause A.2.2.2"
::={ rmcPassageCtrlEntry 4 }

--3.4.4.1.5	Passage Detector Dependent No Activity Threshold
rmcPassageDependNoActivity   OBJECT-TYPE
SYNTAX   INTEGER (0..255)
ACCESS   read-write
STATUS   mandatory
DESCRIPTION 
"If the input on the passage detector for a metered lane has not been actuated, while more vehicles than indicated by this threshold have been counted on the demand detector of the same metered lane and the rmcDemandMode-object is not 'recalled' and the rmcDemandStatus is 'working', the rmcPassageErrorStstus-object for that metered lane shall be set to a value of 'depNoActivity'. 
This value shall be expressed in 1-vehicle increments. 
A suggested usable range is 0 to 30. 
A value of zero (0) shall inhibit the dependent no activity testing.
<Unit> number
<Object Identifier> 1.3.6.1.4.1.1206.4.2.2.3.5.1.1.5"
REFERENCE
"See Clause A.2.2.2"
::={ rmcPassageCtrlEntry 5 }

--3.4.4.2	Passage Detector Status Table
rmcPassageStatTable   OBJECT-TYPE
SYNTAX   SEQUENCE OF RmcPassageStatEntry
ACCESS   not-accessible
STATUS   mandatory
DESCRIPTION 
"A table containing the status information for a passage detector. 
<Table Type> static
<Object Identifier> 1.3.6.1.4.1.1206.4.2.2.3.5.2"
::={ rmcPassage 2 }

rmcPassageStatEntry   OBJECT-TYPE
SYNTAX   RmcPassageStatEntry
ACCESS   not-accessible
STATUS   mandatory
DESCRIPTION 
"Status parameters of the passage detector table. This table is directly correlated to the Passage Detector Configuration and Control Table, which means that the number of rows in this table is exactly the same as the number of rows in the Passage Detector Configuration and Control Table (AUGMENT TABLE in SNMPv2 terminology). Table management can only take place through the PassagDetector Configuration and Control Table, while this table provides 
status information for the associated passage detector. 
<Object Identifier> 1.3.6.1.4.1.1206.4.2.2.3.5.2.1"
INDEX { rmcMeterNumber }
::={ rmcPassageStatTable 1 }

RmcPassageStatEntry ::=SEQUENCE {
	rmcPassageStatus          INTEGER,
	rmcHistPassageStatus      INTEGER, -- added in version 2
	rmcPassageVehicleCount    INTEGER, -- added in version 2
	rmcRedViolationCount      INTEGER -- added in version 2
	}

--3.4.4.2.1	Passage Detector Status
rmcPassageStatus   OBJECT-TYPE
SYNTAX   INTEGER {
   recalled (1),
   working (2),
   otherError (3),
   erraticCount (4),
   maxPresence (5),
   noActivity (6), -- spelling was corrected in version 2
   errorAtSensor (7),
   depNoActivity (8) -- added in version 2
   } 
ACCESS   read-only
STATUS   mandatory
DESCRIPTION
"Indicates the status of the passage detector. The values are:
recalled - indicates that the value of the rmcPassageMode-object is 'recalled'.
working - that this detector has no error.
otherError - indicates an error not defined here. See Operator's manual.
erraticCount - indicates that the vehicle count for this detector has exceeded the value of its rmcPassageErraticCount-object.
maxPresence - indicates a continuous actuation for this detector that has exceeded the value of its rmcPassageMaxPresence-object.
noActivity - indicates a continuous non-actuation for this detector that has exceeded the value of its rmcPassageNoActivity-object.
errorAtSensor - indicates that the sensor for this detector has reported an error. See Operator's manual.
depNoActivity - indicates a continuous non-actuation for this detector,while a count of vehicles on the demand detector in the same metered lane that has exceeded the value of its rmcPassageDependNoActivity-object.
<Object Identifier> 1.3.6.1.4.1.1206.4.2.2.3.5.2.1.1"
REFERENCE
"See Clause A.2.2.2"
::={ rmcPassageStatEntry 1 }

--3.4.4.2.2	Historical Passage Detector Status
rmcHistPassageStatus  OBJECT-TYPE
SYNTAX   INTEGER (0..65535) -- BITMAP16
ACCESS   read-only
STATUS   mandatory
DESCRIPTION
"Indicates the cumulative status of the passage detector. The values are:
<Format> 
Bit Number    Name     Description
Bit 15:     reserved
Bit 14:     reserved
Bit 13:     reserved
Bit 12:     reserved
Bit 11:     reserved
Bit 10:     reserved
Bit 09:     reserved
Bit 08:     reserved
Bit 07:     Dependent No activity - the rmcPassageStatus-object has or had
                        a value of 'depNoActivity' since reset.
Bit 06:     Error at Sensor - the rmcPassageStatus-object has or had
                        a value of 'ErrorAtSensor' since reset.
Bit 05:     No activity - the rmcPassageStatus-object has or had
                        a value of 'noActivity' since reset.
Bit 04:     Max presence - the rmcPassageStatus-object has or had
                        a value of 'maxPresence' since reset.
Bit 03:     Erratic count - the rmcPassageStatus-object has or had
                        a value of 'erraticCount' since reset.
Bit 02:     Other error - the rmcPassageStatus-object has or had
                        a value of 'otherError' since reset.
Bit 01:     Working    - the rmcPassageStatus-object has or had 
                        a value of 'Working' since reset.
Bit 00:     Disabled   - the rmcPassageStatus-object has or had 
                        a value of 'Disabled' since reset.

In the context of this object, 'reset' means either an initialization of the 
RMC or a successful SET of the rmcHistDetectorReset-object. When a 'reset' 
occurs, all bits shall be set to 0.

All reserved bits shall always be set to zero (0). A bad value error shall 
be returned, if a management application writes a one (1) to any of the 
reserved bits.

<Object Identifier> 1.3.6.1.4.1.1206.4.2.2.3.5.2.1.2"
REFERENCE
"See Clause A.2.2.2"
::={ rmcPassageStatEntry 2 }

--3.4.4.2.3	Passage Vehicle Count
rmcPassageVehicleCount   OBJECT-TYPE
SYNTAX   INTEGER (0..255)
ACCESS   read-only
STATUS   mandatory
DESCRIPTION
"Indicates the number of actuations of the passage detector in the most recently completed calculation interval.
<Unit> number
<Object Identifier> 1.3.6.1.4.1.1206.4.2.2.3.5.2.1.3"
REFERENCE
"See Clause A.2.2.2"
::={ rmcPassageStatEntry 3 }

--3.4.4.2.4	Red Violation Count
rmcRedViolationCount   OBJECT-TYPE
SYNTAX   INTEGER (0..255)
ACCESS   read-only
STATUS   mandatory
DESCRIPTION
"Indicates the number of violations detected during the red time in the most recently completed calculation interval.
<Unit> number
<Object Identifier> 1.3.6.1.4.1.1206.4.2.2.3.5.2.1.4"
REFERENCE
"See Clause A.2.2.2"
::={ rmcPassageStatEntry 4 }

--3.4.5	Historic Detector Reset Parameter
rmcHistDetectorReset  OBJECT-TYPE
SYNTAX   INTEGER (0.. 4294967295)
ACCESS   read-write
STATUS   mandatory
DESCRIPTION
"Provides a means to reset all of the Historic Detector Status objects that are used for the various types of detectors, if present. 
A SET (write) of this object shall reset the referenced objects.
A GET (read) of this object shall return the value of 'globalTime' to indicate the time at which the last reset of the historical error status objects occurred. 
If this object is set, the value of the following objects shall be set to '0':
- rmcMLHistLeadStatus-object,
- rmcMLHistTrailStatus-object,
- rmcHistDemandStatus-object,
- rmcHistMergeStatus-object,
- rmcHistQueueStatus-object,
- rmcHistPassageStatus-object

<Object Identifier> 1.3.6.1.4.1.1206.4.2.2.3.2.4.1.6"
REFERENCE
"See Clause A.2.3.1"
::={ rmcMeter 6 }

--3.5	Metering Plan Node
meteringPlan   OBJECT IDENTIFIER  ::={ ramp 4 }
-- This node is an identifier used to group all objects for the configuration 
-- of the metering plans that are common to all ramp meter control units. 
-- Each defined metering plan can be used with any metered lane by association 
-- within the rmcMeterCtrlTable.

--3.5.1	Maximum Number of Metering Plans
rmcMaxNumMeteringPlans   OBJECT-TYPE
SYNTAX   INTEGER (1..255)
ACCESS   read-only
STATUS   mandatory
DESCRIPTION 
"Indicates the maximum number of metering plans that can be stored in the Metering Plan Table. 
A suggested minimum number of plans is four (4). 
<Unit> number
<Object Identifier> 1.3.6.1.4.1.1206.4.2.2.4.1"
REFERENCE
"See Clause A.7.1"
::={ meteringPlan 1 }

--3.5.2	Number of Metering Plans
rmcNumMeteringPlans   OBJECT-TYPE
SYNTAX   INTEGER (1..255)
ACCESS   read-only
STATUS   mandatory
DESCRIPTION 
"Indicates the actual number of metering plans that are present in the Metering Plan Table. This value shall not exceed the value of the 
rmcMaxNumMeteringPlans-object.
<Unit> number
<Object Identifier> 1.3.6.1.4.1.1206.4.2.2.4.2"
REFERENCE
"See Clause A.7.1"
::={ meteringPlan 2 }

--3.5.3	Maximum Number of Levels per Metering Plan
rmcMaxNumLevelsPerPlan   OBJECT-TYPE
SYNTAX   INTEGER (1..255)
ACCESS   read-only
STATUS   mandatory
DESCRIPTION 
"Indicates the maximum number of metering levels that can be stored in EACH metering plan. 
A suggested minimum number of levels per metering plan is three (3).
<Unit> number
<Object Identifier> 1.3.6.1.4.1.1206.4.2.2.4.3"
REFERENCE
"See Clause A.7.1"
::={ meteringPlan 3 }

--3.5.4	Number of Metering Levels
rmcNumMeteringLevels   OBJECT-TYPE
SYNTAX   INTEGER (1..255)
ACCESS   read-only
STATUS   deprecated
DESCRIPTION 
"Indicates the actual number of levels that are present in the ENTIRE metering plan table. This value shall not exceed the product of the value of the rmcMaxNumLevelsPerPlan-object times the value of the rmcMaxNumMeteringPlans object.
<Unit> number
<Object Identifier> 1.3.6.1.4.1.1206.4.2.2.4.4"
REFERENCE
"See Clause A.7.1"
::={ meteringPlan 4 }
-- USERS TAKE NOTE OF MULTIPLE VERSIONS - this object was deprecated in 
-- version 02. The reason is that this object does no longer provide any
-- useful functionality. This is due to the fact that the following table
-- description was updated to follow the requirements of NTCIP 8004v2. No
-- backwards compatibility issues are expected because this was a
-- status/reporting object.

--3.5.5	Metering Plan Table
rmcMeteringPlanTable   OBJECT-TYPE
SYNTAX   SEQUENCE OF RmcMeteringPlanEntry
ACCESS   not-accessible
STATUS   mandatory
DESCRIPTION 
"A table containing the configuration information for a metering level entry in a metering plan. 
<Table Type> static
<Object Identifier> 1.3.6.1.4.1.1206.4.2.2.4.5"
::={ meteringPlan 5 }

rmcMeteringPlanEntry   OBJECT-TYPE
SYNTAX   RmcMeteringPlanEntry
ACCESS   not-accessible
STATUS   mandatory
DESCRIPTION 
"Configuration parameters of the metering plan table. A particular row of this table can be managed using the rmcMeteringRate-object. A level within a metering plan is unused when the value of the rmcMeteringRate-object has been set to '0'. 
The entries in this table are intended for use by every metered lane, if the associated command action is 'trafficResponsive'. The associated rmcXxxxPlan-object (Xxxx is a placeholder for all mentioned possible metering plans) will point to a particular metering plan number. 
<Object Identifier> 1.3.6.1.4.1.1206.4.2.2.4.5.1"
INDEX { rmcMeteringPlanNumber, rmcMeteringLevel }
::={ rmcMeteringPlanTable 1 }

RmcMeteringPlanEntry ::=SEQUENCE {
   rmcMeteringPlanNumber   INTEGER,
   rmcMeteringLevel        INTEGER,
   rmcMeteringRate         INTEGER,
   rmcFlowRateThreshold    INTEGER,
   rmcOccupancyThreshold   INTEGER,
   rmcSpeedThreshold       INTEGER }

--3.5.5.1	Metering Plan Number
rmcMeteringPlanNumber   OBJECT-TYPE
SYNTAX   INTEGER (1..255)
ACCESS   read-only
STATUS   mandatory
DESCRIPTION
"Primary key into this table defining an enumerated listing of row entries that indicate the number of metering plans stored for this RMC unit. This value shall not exceed the value of the rmcMaxNumMeteringPlans-object. 
This is the object pointed to by all rmcXxxxPlan-objects.
<Unit> number
<Object Identifier> 1.3.6.1.4.1.1206.4.2.2.4.5.1.1"
REFERENCE
"See Clause A.7.1"
::={ rmcMeteringPlanEntry 1 }

--3.5.5.2	Metering Level
rmcMeteringLevel   OBJECT-TYPE
SYNTAX   INTEGER (1..255)
ACCESS   read-only
STATUS   mandatory
DESCRIPTION
"Secondary key into this table defining an enumerated listing of row entries that indicate the number of metering levels stored for this RMC unit and the associated metering plan. This value shall not exceed the value of the rmcMaxNumLevelsPerPlan-object.
<Unit> number
<Object Identifier> 1.3.6.1.4.1.1206.4.2.2.4.5.1.2"
REFERENCE
"See Clause A.7.1"
::={ rmcMeteringPlanEntry 2 }
-- USERS TAKE NOTE OF MULTIPLE VERSIONS -
-- the INTEGER range was changed to start at 1 instead of 0. This
-- does not cause backwards compatibility problems because this object would
-- not have been supported, if the function was not supported in the device. 
-- Additionally, an index field of an SNMP table cannot have a value of '0'.

--3.5.5.3	Metering Rate
rmcMeteringRate   OBJECT-TYPE
SYNTAX   INTEGER (0..65535)
ACCESS   read-write
STATUS   mandatory
DESCRIPTION
"Indicates the metering rate which corresponds to this metering level. A suggested usable range is 0, 120 to 1800 in 1-vph increments. 
A value of zero (0) indicates that the ENTIRE level shall not be used during traffic responsive metering, including queue override adjustment.
<Unit> vehicles per hour
<Object Identifier> 1.3.6.1.4.1.1206.4.2.2.4.5.1.3"
REFERENCE
"See Clause A.7.1"
::={ rmcMeteringPlanEntry 3 }

--3.5.5.4	Flow Rate Threshold
rmcFlowRateThreshold   OBJECT-TYPE
SYNTAX   INTEGER (0..65535)
ACCESS   read-write
STATUS   mandatory
DESCRIPTION
"Indicates the average flow rate threshold, which corresponds to this metering plan and level. 
This value shall be expressed in 1-vph increments. 
A suggested usable range is 0, 1000 to 3600. 
A value of zero (0) indicates that this threshold shall NOT be used with flow rate during traffic responsive metering.
<Unit> vehicles per hour
<Object Identifier> 1.3.6.1.4.1.1206.4.2.2.4.5.1.4"
REFERENCE
"See Clause A.7.1"
::={ rmcMeteringPlanEntry 4 }

--3.5.5.5	Occupancy Threshold
rmcOccupancyThreshold   OBJECT-TYPE
SYNTAX   INTEGER (0..65535)
ACCESS   read-write
STATUS   mandatory
DESCRIPTION
"Indicates the average occupancy threshold, which corresponds to this metering plan and level. 
This value shall be expressed in 0.1-percent increments (i.e, 40 = 4.0 percent). 
A suggested usable range is 0 and 50 to 300. 
A value of zero (0) indicates that this threshold shall NOT be used with occupancy during traffic responsive metering.
<Unit> tenth of percent
<Object Identifier> 1.3.6.1.4.1.1206.4.2.2.4.5.1.5"
REFERENCE
"See Clause A.7.1"
::={ rmcMeteringPlanEntry 5 }

--3.5.5.6	Speed Threshold
rmcSpeedThreshold   OBJECT-TYPE
SYNTAX   INTEGER (0..255)
ACCESS   read-write
STATUS   mandatory
DESCRIPTION
"Indicates the average speed threshold, which corresponds to this metering plan and level. 
This value shall be expressed in 1-km/h increments. 
A suggested usable range is 0, 15 to 100. 
A value of zero (0) indicates that this threshold shall NOT be used with speed during traffic responsive metering.
<Unit> kilometer per hour
<Object Identifier> 1.3.6.1.4.1.1206.4.2.2.4.5.1.6"
REFERENCE
"See Clause A.7.1"
::={ rmcMeteringPlanEntry 6 }


--3.6	Scheduling Action Objects
rmcTimebase  OBJECT IDENTIFIER ::={ ramp 5 }
-- This node is an identifier used to group all ramp meter control control 
-- unit-specific objects supporting timebased scheduling.

--3.6.1	Maximum Number of TBC Actions
rmcMaxNumTBCActions   OBJECT-TYPE
SYNTAX   INTEGER (1..255)
ACCESS   read-only
STATUS   mandatory
DESCRIPTION 
"Indicates the maximum number of timebase control actions that can be stored in the (Timebase Control) Action Table.
<Unit> number
<Object Identifier> 1.3.6.1.4.1.1206.4.2.2.5.1"
REFERENCE
"See Clause A.3.1"
::={ rmcTimebase 1 }
-- USERS TAKE NOTE OF MULTIPLE VERSIONS -
-- the INTEGER range was changed to start at 1 instead of 0. This
-- does not cause backwards compatibility problems because this object would
-- not have been supported, if the function was not supported in the device.

--3.6.2	Number of TBC Actions
rmcNumTBCActions   OBJECT-TYPE
SYNTAX   INTEGER (1..255)
ACCESS   read-only
STATUS   mandatory
DESCRIPTION 
"Indicates the actual number of timebase control actions that are present in 
the (Timebase Control) Action Table. 
This value shall not exceed the value of the rmcMaxNumTBCActions-object.
<Unit> number
<Object Identifier> 1.3.6.1.4.1.1206.4.2.2.5.2"
REFERENCE
"See Clause A.3.1"
::={ rmcTimebase 2 }
-- USERS TAKE NOTE OF MULTIPLE VERSIONS -
-- the INTEGER range was changed to start at 1 instead of 0. This
-- does not cause backwards compatibility problems because this object would
-- not have been supported, if the function was not supported in the device.

--3.6.3	Timebase Control Action Table
rmcActionTable   OBJECT-TYPE
SYNTAX   SEQUENCE OF RmcActionEntry
ACCESS   not-accessible
STATUS   mandatory
DESCRIPTION 
"A table containing the actions that can be selected based on a time based scheduler. The scheduler will determine when an action shall be selected. The dayPlanTable of the scheduler (see Global Object Definitions) points to a row in this table to identify the action to be activated.
<Table Type> static
<Object Identifier> 1.3.6.1.4.1.1206.4.2.2.5.3"
REFERENCE 
"NTCIP 1201, timebase-node"
::={ rmcTimebase 3 }

rmcActionEntry   OBJECT-TYPE
SYNTAX   RmcActionEntry
ACCESS   not-accessible
STATUS   mandatory
DESCRIPTION 
"Parameters of the Timebase Control Action Table. A particular row of this 
table can be managed using the rmcActionMode-object. An action described 
within a row is unused when the value of that object has been set to zero (0).
<Object Identifier> 1.3.6.1.4.1.1206.4.2.2.5.3.1"
INDEX { rmcActionNum }
::={ rmcActionTable 1 }

RmcActionEntry ::=SEQUENCE {
	rmcActionNum        INTEGER,
	rmcActionMode       INTEGER,
	rmcMeterActionNum   INTEGER,
	rmcMLActionNum      INTEGER }

--3.6.3.1	Action Number
rmcActionNum   OBJECT-TYPE
SYNTAX   INTEGER (1..255) 
ACCESS   read-only
STATUS   mandatory
DESCRIPTION 
"Enumerated listing of row entries. The value of this object cannot exceed the value of the rmcMaxNumTBCActions-object. This is the object to which the dayPlanAction-object within the Global Object Definitions points. 
<Unit> number
<Object Identifier> 1.3.6.1.4.1.1206.4.2.2.5.3.1.1"
REFERENCE
"See Clause A.3.1"
::={ rmcActionEntry 1 }

--3.6.3.2	Action Mode
rmcActionMode   OBJECT-TYPE
SYNTAX   INTEGER (0..1)
ACCESS   read-write
STATUS   mandatory
DESCRIPTION
"Indicates whether this row is used. 
0 = false - this row is NOT used.
1 = true - this row is used. 
<Object Identifier> 1.3.6.1.4.1.1206.4.2.2.5.3.1.2"
::={ rmcActionEntry 2 }

--3.6.3.3	Metered Lane Action Number
rmcMeterActionNum   OBJECT-TYPE
SYNTAX   INTEGER (0..255) 
ACCESS   read-write
STATUS   mandatory
DESCRIPTION 
"This object is used to point to a value of the rmcMeterActionIndex-object. 
A value of zero (0) indicates that there are no Metered Lane action items
associated with this Action Index. 
This value shall not exceed the value of the rmcNumMeterTBCActions-object.
<Unit> number
<Object Identifier> 1.3.6.1.4.1.1206.4.2.2.5.3.1.3"
::={ rmcActionEntry 3 }

--3.6.3.4	Mainline Lane Action Number
rmcMLActionNum   OBJECT-TYPE
SYNTAX   INTEGER (0..255) 
ACCESS   read-write
STATUS   mandatory
DESCRIPTION 
"This object is used to point to a value of the rmcMLActionIndex-object.
A value of zero (0) indicates that there are no Mainline Lane action items associated with this Action Index. 
This value shall not exceed the value of the rmcNumMLTBCActions-object.
<Unit> number
<Object Identifier> 1.3.6.1.4.1.1206.4.2.2.5.3.1.4"
::={ rmcActionEntry 4 }

--3.6.4	Maximum Number of Metered Lane TBC Actions
rmcMaxNumMeterTBCActions   OBJECT-TYPE
SYNTAX   INTEGER (1..255)
ACCESS   read-only
STATUS   mandatory
DESCRIPTION 
"Indicates the maximum number of metered lane timebase control actions that can be stored in the Metered Lane Timebase Control Action table. 
<Unit> number
<Object Identifier> 1.3.6.1.4.1.1206.4.2.2.5.4"
REFERENCE
"See Clause A.3.1"
::={ rmcTimebase 4 }
-- USERS TAKE NOTE OF MULTIPLE VERSIONS -
-- the INTEGER range was changed to start at 1 instead of 0. This
-- does not cause backwards compatibility problems because this object would
-- not have been supported, if the function was not supported in the device.

--3.6.5	Number of Metered Lane TBC Actions
rmcNumMeterTBCActions   OBJECT-TYPE
SYNTAX   INTEGER (1..255)
ACCESS   read-only
STATUS   mandatory
DESCRIPTION 
"Indicates the actual number of metered lane timebase control actions that are present in this Metered Lane Timebase Control Action table. 
This value shall not exceed the value of the rmcMaxNumMeterTBCActions-object.
<Unit> number
<Object Identifier> 1.3.6.1.4.1.1206.4.2.2.5.5"
REFERENCE
"See Clause A.3.1"
::={ rmcTimebase 5 }
-- USERS TAKE NOTE OF MULTIPLE VERSIONS -
-- the INTEGER range was changed to start at 1 instead of 0. This
-- does not cause backwards compatibility problems because this object would
-- not have been supported, if the function was not supported in the device.

--3.6.6	Metered Lane Timebase Control Action Table
rmcMeterActionTable   OBJECT-TYPE
SYNTAX   SEQUENCE OF RmcMeterActionEntry
ACCESS   not-accessible
STATUS   mandatory
DESCRIPTION 
"A table containing the metered lane actions that can be selected based on a time-based scheduler. The rows within this table are pointed to by the rmcMeterActionNum-object within the rmcActionTable. 
This table is double-indexed describing what action to execute for which metered lane.
<Table Type> static
<Object Identifier> 1.3.6.1.4.1.1206.4.2.2.5.6"
::={ rmcTimebase 6 }

rmcMeterActionEntry   OBJECT-TYPE
SYNTAX   RmcMeterActionEntry
ACCESS   not-accessible
STATUS   mandatory
DESCRIPTION 
"Parameters of the Timebase Control Action Table for a metered lane. 
A particular row of this table can be managed using the rmcMeterActionMode-object. An action described within a row is unused when the value of that object has been set to zero (0).
<Object Identifier> 1.3.6.1.4.1.1206.4.2.2.5.6.1"
INDEX { rmcMeterActionIndex, rmcMeterNumber }
::={ rmcMeterActionTable 1 }

RmcMeterActionEntry ::=SEQUENCE {
	rmcMeterActionIndex      INTEGER,
	rmcMeterActionMode       INTEGER,
	rmcTBActionCtrl          INTEGER,
	rmcTBPlanCtrl            INTEGER,
	rmcTBRateCtrl            INTEGER,
	rmcTBVehiclesPerGrnCtrl  INTEGER,
	rmcTBCMinMeterRateCtrl   INTEGER,
	rmcTBCMaxMeterRateCtrl   INTEGER }

--3.6.6.1	Metered Lane Action Index
rmcMeterActionIndex   OBJECT-TYPE
SYNTAX   INTEGER (1..255) 
ACCESS   read-only
STATUS   mandatory
DESCRIPTION 
"Primary index to this double indexed table showing an enumerated listing of row entries. The value of the rmcMeterActionNum-object is pointing to THIS object,not to a particular row. All rows that are associated with this primary key will be activated if the scheduler points to the appropriate row within the rmcActionTable.
The value of this object shall not exceed the value of the rmcMaxNumMeterTBCActions-object nor that of the rmcNumMeterTBCActions-
object.
<Unit> number
<Object Identifier> 1.3.6.1.4.1.1206.4.2.2.5.6.1.1"
::={ rmcMeterActionEntry 1 }

--3.6.6.2	Metered Lane Action Mode
rmcMeterActionMode   OBJECT-TYPE
SYNTAX   INTEGER (0..1)
ACCESS   read-write
STATUS   mandatory
DESCRIPTION
"Indicates whether this row is used. 
0 = false - this row is NOT being used.
1 = true - this row is used. 
<Object Identifier> 1.3.6.1.4.1.1206.4.2.2.5.6.1.2"
::={ rmcMeterActionEntry 2 }

--3.6.6.3	Timebase Action Control
rmcTBActionCtrl   OBJECT-TYPE
SYNTAX   INTEGER {
   dark (1),
   restInGreen (2),
   fixedRate (3),
   trafficResponsive (4),
   emergencyGreen (5),
   skip (6) }
ACCESS   read-write
STATUS   mandatory
DESCRIPTION 
"Indicates the action that may be active if the metered lane is controlled by 
timebase control. This object is used to control the entry, while the
rmcTBActionStatus-object indicates the status. The values are:
dark - indicates that the metered lane will advance to the Pre-Metering 
    Non-Green interval.
restInGreen - indicates that the metered lane will advance to  the 
    Pre-Metering Green interval.
fixedRate - indicates that the metered lane will operate using the value of
    the rmcTBRateCtrl-object.
trafficResponsive -indicates that the metered lane will operate using
    mainline station traffic conditions and the value of the 
    rmcTBPlanCtrl-object.
emergencyGreen - indicates that the metered lane will advance to the 
    Post-metering Green interval without entering the Shutdown Green, 
    Shutdown Yellow, Shutdown Red or Shutdown Warning intervals when the
    metered lane is NOT in the Non-metering state. The metered lane will
    advance to the Pre-Metering Green interval when the metered lane is
    in the Non-metering state.
skip - indicates that the next-lower level command source shall be
    considered as specified by the rmcCmdSourcePriorityOrder-object. 
<Object Identifier> 1.3.6.1.4.1.1206.4.2.2.5.6.1.3"
REFERENCE
"See Clause A.3.1"
::={ rmcMeterActionEntry 3 }

--3.6.6.4	Timebase Plan Control
rmcTBPlanCtrl   OBJECT-TYPE
SYNTAX   INTEGER (0..255)
ACCESS   read-write
STATUS   mandatory
DESCRIPTION
"Indicates the metering plan number that to be used if the metered lane is commanded by timebase control and the rmcImplementAction-object has a value of 'trafficResponsive'. This value shall not exceed the value of the rmcMaxNumMeterPlans-object. 
This object is used to control the entry, while the rmcTBPlanStatus-object indicates the status. 
<Unit> number
<Object Identifier> 1.3.6.1.4.1.1206.4.2.2.5.6.1.4"
REFERENCE
"See Clause A.3.1"
::={ rmcMeterActionEntry 4 }

--3.6.6.5	Timebase Rate Control
rmcTBRateCtrl   OBJECT-TYPE
SYNTAX   INTEGER (0..65535)
ACCESS   read-write
STATUS   mandatory
DESCRIPTION
"Indicates the metering rate that to be used if the metered lane is commanded by timebase control and the rmcImplementAction-object has a value of 'fixedRate'. This object is used to control the entry, while the rmcTBRateStatus-object indicates the status. 
This value shall be expressed in 1-vph increments. 
A suggested usable range is 120 to 1800. 
<Unit> vehicles per hour
<Object Identifier> 1.3.6.1.4.1.1206.4.2.2.5.6.1.5"
REFERENCE
"See Clause A.3.1"
::={ rmcMeterActionEntry 5 }

--3.6.6.6	Timebase Vehicles-Per-Green Control
rmcTBVehiclesPerGrnCtrl   OBJECT-TYPE
SYNTAX   INTEGER (0..255)
ACCESS   read-write
STATUS   mandatory
DESCRIPTION
"Indicates the number of vehicles that are allowed to pass during the green and yellow intervals of one cycle while the metered lane is commanded by timebase control. This object is used to control the entry, while the rmcTBVehiclesPerGrnStatus-object indicates the status. 
This value shall be expressed in 1-vehicle increments. 
A suggested usable range is 1 to 5.
<Unit> number
<Object Identifier> 1.3.6.1.4.1.1206.4.2.2.5.6.1.6"
REFERENCE
"See Clause A.3.1"
::={ rmcMeterActionEntry 6 }

--3.6.6.7	Timebase Control Minimum Metering Rate Control
rmcTBCMinMeterRateCtrl   OBJECT-TYPE
SYNTAX   INTEGER (0..65535)
ACCESS   read-write
STATUS   mandatory
DESCRIPTION
"Indicates the operational minimum metering rate. This object is used to control the entry, while the rmcTBCMinMeterRateStatus-object indicates the status.
This value shall be less than or equal to the rmcTBCMaxMeterRateCtrl-object.
This value shall be expressed in 1-vph increments. 
A suggested usable range is 0, 120 to 1800. 
A value of zero (0) indicates this parameter shall not be used. 
<Unit> vehicles per hour
<Object Identifier> 1.3.6.1.4.1.1206.4.2.2.5.6.1.7"
REFERENCE
"See Clause A.3.1"
::={ rmcMeterActionEntry 7 }

--3.6.6.8	Timebase Control  Maximum Metering Rate Control
rmcTBCMaxMeterRateCtrl   OBJECT-TYPE
SYNTAX   INTEGER (0..65535)
ACCESS   read-write
STATUS   mandatory
DESCRIPTION
"Indicates the operational maximum metering rate. This object is used to control the entry, while the rmcTBCMaxMeterRateStatus-object indicates the status. 
This value shall be expressed in 1-vph increments. 
A suggested usable range is 0, 120 to 1800. 
A value of zero (0) indicates this parameter shall not be used. 
The value, if non-zero, shall be greater than or equal to the value of the rmcTBCMinMeterRateCtrl-object. 
<Unit> vehicles per hour
<Object Identifier> 1.3.6.1.4.1.1206.4.2.2.5.6.1.8"
REFERENCE
"See Clause A.3.1"
::={ rmcMeterActionEntry 8 }

--3.6.7	Maximum Number of Mainline Lane TBC Actions
rmcMaxNumMLTBCActions   OBJECT-TYPE
SYNTAX   INTEGER (1..255)
ACCESS   read-only
STATUS   mandatory
DESCRIPTION 
"Indicates the maximum number of timebase control actions that can be stored in the Mainline Lane Timebase Control Action Table. 
<Unit> number
<Object Identifier> 1.3.6.1.4.1.1206.4.2.2.5.7"
::={ rmcTimebase 7 }
-- USERS TAKE NOTE OF MULTIPLE VERSIONS -
-- the INTEGER range was changed to start at 1 instead of 0. This
-- does not cause backwards compatibility problems because this object would
-- not have been supported, if the function was not supported in the device.

--3.6.8	Number of Mainline Lane TBC Actions
rmcNumMLTBCActions   OBJECT-TYPE
SYNTAX   INTEGER (1..255)
ACCESS   read-only
STATUS   mandatory
DESCRIPTION 
"Indicates the actual number of timebase control actions that are present in the Mainline Lane Timebase Control Action Table. 
This value shall not exceed the value of the rmcMaxNumMLTBCActions-object.
<Unit> number
<Object Identifier> 1.3.6.1.4.1.1206.4.2.2.5.8"
::={ rmcTimebase 8 }
-- USERS TAKE NOTE OF MULTIPLE VERSIONS -
-- the INTEGER range was changed to start at 1 instead of 0. This
-- does not cause backwards compatibility problems because this object would
-- not have been supported, if the function was not supported in the device.

--3.6.9	Mainline Timebase Control Action Table
rmcMLActionTable   OBJECT-TYPE
SYNTAX   SEQUENCE OF   RmcMLActionEntry
ACCESS   not-accessible
STATUS   mandatory
DESCRIPTION 
"A table containing the actions for mainline lanes that can be selected based 
on a time based scheduler. The rows within this table are pointed to by the
rmcMLActionNum-object within the rmcActionTable-object. This is a double
indexed table describing what action to execute for which mainline lane. 
<Table Type> static
<Object Identifier> 1.3.6.1.4.1.1206.4.2.2.5.9"
::={ rmcTimebase 9 }

rmcMLActionEntry   OBJECT-TYPE
SYNTAX   RmcMLActionEntry
ACCESS   not-accessible
STATUS   mandatory
DESCRIPTION 
"Parameters of the Timebase Control Action Table for A mainline lane. 
A particular row of this table can be managed using the rmcMLActionMode-object.
An action described within a row is unused when the value of that object has
been set to zero (0). 
<Object Identifier> 1.3.6.1.4.1.1206.4.2.2.5.9.1"
INDEX { rmcMLActionIndex, rmcMLNumber }
::={ rmcMLActionTable 1 }

RmcMLActionEntry ::=SEQUENCE {
rmcMLActionIndex     INTEGER,
rmcMLActionMode      INTEGER,
rmcTBMLUsageMode     INTEGER
}

--3.6.9.1	Mainline Lane Action Index
rmcMLActionIndex   OBJECT-TYPE
SYNTAX   INTEGER (1..255) 
ACCESS   read-only
STATUS   mandatory
DESCRIPTION 
"Primary index to this double indexed table showing an enumerated listing of row entries. The value of the rmcMLActionNum-object is pointing to THIS object, not to a particular row. All rows that are associated with this primary key will be activated if the scheduler points to the appropriate row within the rmcActionTable. 
The value of this object cannot exceed the value of the rmcMaxNumMLTBCActions-object. 
<Unit> number
<Object Identifier> 1.3.6.1.4.1.1206.4.2.2.5.9.1.1" 
::={ rmcMLActionEntry 1 }

--3.6.9.2	Mainline Lane Action Mode
rmcMLActionMode   OBJECT-TYPE
SYNTAX   INTEGER (0..1) 
ACCESS   read-write
STATUS   mandatory
DESCRIPTION
"Indicates whether this row is used. The values are:
 0 - false. This row is NOT being used
 1 - true. This row is being used. 
<Object Identifier> 1.3.6.1.4.1.1206.4.2.2.5.9.1.2" 
::={ rmcMLActionEntry 2 }

--3.6.9.3	Timebase Control Lane Usage Mode
rmcTBMLUsageMode   OBJECT-TYPE
SYNTAX   INTEGER {
   notUsed (1),
   schemeF (2),
   schemeO (3),
   schemeFO (4),
   schemeS (5),
   schemeFS (6),
   schemeOS (7),
   schemeFOS (8) }
ACCESS   read-write
STATUS   mandatory
DESCRIPTION
"Indicates which mainline station traffic parameters will use the data from this lane based on time of day. This object shall take precedence over the value entered in the rmcMLUsageMode-object (defined in the rmcMLCtrlTable). This precedence shall be reflected in the rmcMLUsageStatus-object (defined in the rmcMLStatTable). The values are
notUsed - the lane data will not be used to calculate any mainline station parameter.
schemeF - the lane data will be used to calculate the mainline station flow rate
schemeO - the lane data will be used to calculate the mainline station average occupancy
schemeFO - the lane data will be used to calculate the mainline station flow rate and average occupancy
schemeS - the lane data will be used to calculate the mainline station average speed
schemeFS - the lane data will be used to calculate the mainline station flow rate and average speed
schemeOS - the lane data will be used to calculate the mainline station average occupancy and occupancy speed
schemeFOS - the lane data will be used to calculate the mainline station flow rate, average occupancy and average speed. 
<Object Identifier> 1.3.6.1.4.1.1206.4.2.2.5.9.1.3"
REFERENCE
"See Clause A.3.1"
::={ rmcMLActionEntry 3 }

--3.7	Physical Input / Output Objects
rmcInOutput  OBJECT IDENTIFIER  ::={ ramp 6 }
-- This node is an identifier used to group all ramp meter control unit-
-- specific objects supporting remote setting of input and output 
-- definitions.

--3.7.1	Advance Warning Sign Output Number
rmcAdvSignOutNumber   OBJECT-TYPE
SYNTAX   INTEGER (0..255)
ACCESS   read-write
STATUS   mandatory
DESCRIPTION
"Indicates the physical output number of the advance warning sign for the entire RMC. A value of 255 indicates that there is no physical output for this function. 
<Unit> number
<Object Identifier> 1.3.6.1.4.1.1206.4.2.2.6.1"
REFERENCE
"See Clause A.10.1"
::={ rmcInOutput 1 }

--3.7.2	Mainline Lane Physical Input Table
rmcMLInTable   OBJECT-TYPE
SYNTAX   SEQUENCE OF RmcMLInEntry
ACCESS   not-accessible
STATUS   mandatory
DESCRIPTION
"A table containing the configuration information for mainline lane physical inputs. 
<Table Type> static
<Object Identifier> 1.3.6.1.4.1.1206.4.2.2.6.2"
REFERENCE
"See Clause A.10.4"
::={ rmcInOutput 2 }

rmcMLInEntry   OBJECT-TYPE
SYNTAX   RmcMLInEntry
ACCESS   not-accessible
STATUS   mandatory
DESCRIPTION
"Configuration parameters of the mainline lane physical input table. This table is directly correlated to the Mainline Lane Configuration and Control Table, which means that the number of rows in this table is exactly the same as the number of rows in the Mainline Lane Configuration and Control Table (AUGMENT TABLE in SNMPv2 terminology). Table management can only take place through the Mainline Lane Configuration and Control Table (rmcMLCtrlTable), while this table defines the associated physical input and outputs. 
<Object Identifier> 1.3.6.1.4.1.1206.4.2.2.6.2.1"
INDEX { rmcMLNumber }
::={ rmcMLInTable 1 }

RmcMLInEntry ::=SEQUENCE {
	rmcMLLeadInNumber         INTEGER,
	rmcMLTrailInNumber        INTEGER }

--3.7.2.1	Leading Detector Input Number
rmcMLLeadInNumber   OBJECT-TYPE
SYNTAX   INTEGER (0..255)
ACCESS   read-write
STATUS   mandatory
DESCRIPTION
"Indicates the physical input number of the leading detector for this mainline lane. A value of 255 indicates that there is no physical input for this function. 
<Unit> number
<Object Identifier> 1.3.6.1.4.1.1206.4.2.2.6.2.1.1"
REFERENCE
"See Clause A.10.4"
::={ rmcMLInEntry 1 }

--3.7.2.2	Trailing Detector Input Number
rmcMLTrailInNumber   OBJECT-TYPE
SYNTAX   INTEGER (0..255)
ACCESS   read-write
STATUS   mandatory
DESCRIPTION
"Indicates the physical input number of the trailing detector for this mainline lane. A value of 255 indicates that there is no physical input for this function. 
<Unit> number
<Object Identifier> 1.3.6.1.4.1.1206.4.2.2.6.2.1.2"
REFERENCE
"See Clause A.10.4"
::={ rmcMLInEntry 2 }

--3.7.3	Queue Detector Physical Input Table
rmcQueueInTable   OBJECT-TYPE
SYNTAX   SEQUENCE OF RmcQueueInEntry
ACCESS   not-accessible
STATUS   mandatory
DESCRIPTION 
"A table containing the configuration information for metered lane queue detection physical inputs and outputs. 
<Table Type> static
<Object Identifier> 1.3.6.1.4.1.1206.4.2.2.6.3"
REFERENCE
"See Clause A.10.4"
::={ rmcInOutput 3 }

rmcQueueInEntry   OBJECT-TYPE
SYNTAX   RmcQueueInEntry
ACCESS   not-accessible
STATUS   mandatory
DESCRIPTION
"Configuration parameters of the metered lane queue detector physical input table. This table is directly correlated to the Queue Detector Configuration and Control Table, which means that the number of rows in this table is exactly the same as the number of rows in the Queue Detector Configuration and Control Table (AUGMENT TABLE in SNMPv2 terminology). Table management can only take place through the rmcQueueDetectMode-object within Queue Detector Configuration and Control Table (rmcQueueCtrlTable), while this
table defines the associated physical input. 
<Object Identifier> 1.3.6.1.4.1.1206.4.2.2.6.3.1"
INDEX { rmcMeterNumber, rmcQueueNum }
::={ rmcQueueInTable 1 }

RmcQueueInEntry ::=SEQUENCE {
	rmcMetQueueInNumber		INTEGER }

--3.7.3.1	Queue Detector Input Number
rmcMetQueueInNumber   OBJECT-TYPE
SYNTAX   INTEGER (0..255)
ACCESS   read-write
STATUS   mandatory
DESCRIPTION
"Indicates the physical input number of the queue detector for the associated metered lane and queue detector number. A value of 255 indicates that there is no physical input for this function. 
<Unit> number
<Object Identifier> 1.3.6.1.4.1.1206.4.2.2.6.3.1.1"
REFERENCE
"See Clause A.10.3.1"
::={ rmcQueueInEntry 1 }

--3.7.4	Metered Lane Physical Input/Output Table
rmcMeterInOutTable   OBJECT-TYPE
SYNTAX   SEQUENCE OF RmcMeterInOutEntry
ACCESS   not-accessible
STATUS   mandatory
DESCRIPTION
"A table containing the configuration information for metered lane physical inputs and outputs. 
<Table Type> static
<Object Identifier> 1.3.6.1.4.1.1206.4.2.2.6.4"
REFERENCE
"See Clause A.10.3"
::={ rmcInOutput 4 }

rmcMeterInOutEntry   OBJECT-TYPE
SYNTAX   RmcMeterInOutEntry
ACCESS   not-accessible
STATUS   mandatory
DESCRIPTION
"Configuration parameters of the metered lane physical input/output table. This table is directly correlated to the Metered Lane Control Table, which means that the number of rows in this table is exactly the same as the number of rows in the Metered Lane Control Table (AUGMENT TABLE in SNMPv2 terminology). Table management can only take place through the Metered Lane Control Table (rmcMeterCtrlTable), while this table defines the associated physical input and outputs. 
<Object Identifier> 1.3.6.1.4.1.1206.4.2.2.6.4.1"
INDEX { rmcMeterNumber }
::={ rmcMeterInOutTable 1 }

RmcMeterInOutEntry ::=SEQUENCE {
	rmcMeterDemandInNumber       INTEGER,
	rmcMeterPassageInNumber      INTEGER,
	rmcMeterRedOutNumber         INTEGER,
	rmcMeterYellowOutNumber      INTEGER,
	rmcMeterGreenOutNumber       INTEGER,
	rmcMeterAdvSignOutNumber     INTEGER}

--3.7.4.1	Demand Detector Input Number
rmcMeterDemandInNumber   OBJECT-TYPE
SYNTAX   INTEGER (0..255)
ACCESS   read-write
STATUS   mandatory
DESCRIPTION
"Indicates the physical input number of the demand detector for this metered lane. A value of 255 indicates that there is no physical input for this function. 
<Unit> number
<Object Identifier> 1.3.6.1.4.1.1206.4.2.2.6.4.1.1"
REFERENCE
"See Clause A.10.3"
::={ rmcMeterInOutEntry 1 }

--3.7.4.2	Passage Detector Input Number
rmcMeterPassageInNumber   OBJECT-TYPE
SYNTAX   INTEGER (0..255)
ACCESS   read-write
STATUS   mandatory
DESCRIPTION
"Indicates the physical input number of the passage detector for this metered lane. A value of 255 indicates that there is no physical input for this function. 
<Unit> number
<Object Identifier> 1.3.6.1.4.1.1206.4.2.2.6.4.1.2"
REFERENCE
"See Clause A.10.3"
::={ rmcMeterInOutEntry 2 }

--3.7.4.3	Red Indication Output Number
rmcMeterRedOutNumber   OBJECT-TYPE
SYNTAX   INTEGER (0..255)
ACCESS   read-write
STATUS   mandatory
DESCRIPTION
"Indicates the physical output number of the red indication for this metered lane. A value of 255 indicates that there is no physical output for this function. 
<Unit> number
<Object Identifier> 1.3.6.1.4.1.1206.4.2.2.6.4.1.3"
REFERENCE
"See Clause A.10.3"
::={ rmcMeterInOutEntry 3 }

--3.7.4.4	Yellow Indication Output Number
rmcMeterYellowOutNumber   OBJECT-TYPE
SYNTAX   INTEGER (0..255)
ACCESS   read-write
STATUS   mandatory
DESCRIPTION
"Indicates the physical output number of the yellow indication for this metered lane. A value of 255 indicates that there is no  physical output for this function. 
<Unit> number
<Object Identifier> 1.3.6.1.4.1.1206.4.2.2.6.4.1.4"
REFERENCE
"See Clause A.10.3"
::={ rmcMeterInOutEntry 4 }

--3.7.4.5	Green Indication Output Number
rmcMeterGreenOutNumber   OBJECT-TYPE
SYNTAX   INTEGER (0..255)
ACCESS   read-write
STATUS   mandatory
DESCRIPTION
"Indicates the physical output number of the green indication for this metered lane. A value of 255 indicates that there is no physical output for this function. 
<Unit> number
<Object Identifier> 1.3.6.1.4.1.1206.4.2.2.6.4.1.5"
REFERENCE
"See Clause A.10.3"
::={ rmcMeterInOutEntry 5 }

--3.7.4.6	Metered Lane Advance Warning Sign Output Number
rmcMeterAdvSignOutNumber   OBJECT-TYPE
SYNTAX   INTEGER (0..255)
ACCESS   read-write
STATUS   mandatory
DESCRIPTION
"Indicates the physical output number of the advance warning sign for this metered lane. A value of 255 indicates that there is no physical output for this function. 
<Unit> number
<Object Identifier> 1.3.6.1.4.1.1206.4.2.2.6.4.1.6"
REFERENCE
"See Clause A.10.3"
::={ rmcMeterInOutEntry 6 }

--3.7.5	Dependency Group Physical Input/Output Table
rmcDependInOutTable   OBJECT-TYPE
SYNTAX   SEQUENCE OF RmcDependInOutEntry
ACCESS   not-accessible
STATUS   mandatory
DESCRIPTION
"A table containing the configuration information for dependency group physical inputs and outputs. 
<Table Type> static
<Object Identifier> 1.3.6.1.4.1.1206.4.2.2.6.5"
REFERENCE
"See Clause A.10.2"
::={ rmcInOutput 5 }

rmcDependInOutEntry   OBJECT-TYPE
SYNTAX   RmcDependInOutEntry
ACCESS   not-accessible
STATUS   mandatory
DESCRIPTION
"Configuration parameters of the dependency group physical input/output table. This table is directly correlated to the Dependency Group Configuration and Control Table, which means that the number of rows in this table is exactly the same as the number of rows in the Dependency Group Configuration and Control Table (AUGMENT TABLE in SNMPv2 terminology). Table management can only take place through the Dependency Group Configuration and Control Table (rmcDependGroupCtrlTable), while this table defines the associated physical
input and outputs. 
<Object Identifier> 1.3.6.1.4.1.1206.4.2.2.6.5.1"
INDEX { rmcDependGroupNumber }
::={ rmcDependInOutTable 1 }

RmcDependInOutEntry ::=SEQUENCE {
	rmcDependMergeInNumber         INTEGER,
	rmcDependAdvSignOutNumber      INTEGER }

--3.7.5.1	Merge Detector Input Number
rmcDependMergeInNumber   OBJECT-TYPE
SYNTAX   INTEGER (0..255)
ACCESS   read-write
STATUS   mandatory
DESCRIPTION
"Indicates the physical input number of the merge detector for this dependency group. A value of 255 indicates that there is no physical input for this function. 
<Unit> number
<Object Identifier> 1.3.6.1.4.1.1206.4.2.2.6.5.1.1"
REFERENCE
"See Clause A.10.2"
::={ rmcDependInOutEntry 1 }

--3.7.5.2	Dependency Group Advance Warning Sign Output Number
rmcDependAdvSignOutNumber   OBJECT-TYPE
SYNTAX   INTEGER (0..255)
ACCESS   read-write
STATUS   mandatory
DESCRIPTION
"Indicates the physical output number of the advance warning sign for this dependency group. A value of 255 indicates that there is no physical output for this function. 
<Unit> number
<Object Identifier> 1.3.6.1.4.1.1206.4.2.2.6.5.1.2"
REFERENCE
"See Clause A.10.2"
::={ rmcDependInOutEntry 2 }

--3.8	Block Objects

rmcBlock  OBJECT IDENTIFIER ::= { ramp 7 }

-- This object is an identifier used to group all objects for 
-- support of RMC Unit Block Upload and Download activities.

--3.8.1	Block Get Control
rmcBlockGetControl   OBJECT-TYPE
SYNTAX   OCTET STRING (SIZE(2..12))
ACCESS   read-write
STATUS   mandatory
DESCRIPTION
"<Definition> An OER encoded string of reference parameters for RMC Block Uploads. The parameter values in this string are:
 rmcBlockDataType    INTEGER (0..255)
 rmcBlockDataID      INTEGER (0..255)
 rmcBlockIndex1      INTEGER (1..255) if needed
 rmcBlockQuantity1   INTEGER (1..255) if needed
 rmcBlockIndex2      INTEGER (1..255) if needed
 rmcBlockQuantity2   INTEGER (1..255) if needed
 rmcBlockIndex3      INTEGER (1..255) if needed
 rmcBlockQuantity3   INTEGER (1..255) if needed
 rmcBlockIndex4      INTEGER (1..255) if needed
 rmcBlockQuantity4   INTEGER (1..255) if needed
 rmcBlockIndex5      INTEGER (1..255) if needed
 rmcBlockQuantity5   INTEGER (1..255) if needed

A GET of rmcBlockData shall utilize values currently 
in this object to define the data to be returned.

A SET of this object shall be evaluated for validity and an Error Status of badValue(3) be returned for the following conditions:
1) rmcBlockDataType is not supported
2) rmcBlockDataID is not supported
3) rmcBlockIndex1 is zero or is greater than the table's maximum number of rows
4) rmcBlockQuantity1 is zero or rmcBlockIndex1 + rmcBlockQuantity1 - 1 is greater than the table's maximum number of rows
5) rmcBlockIndex2 is zero or not supported
6) rmcBlockQuantity2 is zero or rmcBlockIndex2 + rmcBlockQuantity2 - 1 is greater than the table's maximum number of rows
7) rmcBlockIndex3 is zero or is greater than the table's maximum number of rows
8) rmcBlockQuantity3 is zero or rmcBlockIndex3 + rmcBlockQuantity3 - 1 is greater than the table's maximum number of rows
9) rmcBlockIndex4 is zero or is greater than the table's maximum number of rows
10) rmcBlockQuantity4 is zero or rmcBlockIndex4 + rmcBlockQuantity4 - 1 is greater than the table's maximum number of rows
11) rmcBlockIndex5 is zero or is greater than the table's maximum number of rows
12) rmcBlockQuantity5 is zero or rmcBlockIndex5 + rmcBlockQuantity5 - 1 is greater than the table's maximum number of rows
13) if the SET length is zero or incorrect for rmcBlockDataType & rmcBlockDataID
14) if the GetResponse length for a GET on rmcBlockData using maximum data field sizes would exceed a local limitation
When this validity check fails, rmcBlockErrorStatus shall be set equal to the Bullet Value above that generated the error. Because of SNMP, it cannot be determined in advance which error of multiple, simultaneous errors will be reported.

<Object Identifier> 1.3.6.1.4.1.1206.4.2.2.7.1"
::= { rmcBlock 1 }

--3.8.2	Block Data
rmcBlockData   OBJECT-TYPE
SYNTAX   OCTET STRING (SIZE(2..484))
ACCESS  read-write
STATUS  mandatory
DESCRIPTION
"<Definition> An OER encoded string used for uploading and downloading RMC parameters. See SECTION 4 for encoding and decoding the block.

A SET on this object shall require the use of 'dbCreateTransaction' defined in NTCIP 1201 v03 Clause 2.3.1.

A SET of this object shall be evaluated for validity and an Error Status of badValue(3) be returned for the following conditions:
1) rmcBlockDataType is not supported
2) rmcBlockDataID is not supported
3) rmcBlockIndex1 is zero or is greater than the table's maximum number of rows
4) rmcBlockQuantity1 is zero or rmcBlockIndex1 + rmcBlockQuantity1 - 1 is greater than the table's maximum number of rows
5) rmcBlockIndex2 is zero or is greater than the table's maximum number of rows 
6) rmcBlockQuantity2 is zero or rmcBlockIndex2 + rmcBlockQuantity2 - 1 is greater than the table's maximum number of rows
7) rmcBlockIndex3 is zero or is greater than the table's maximum number of rows
8) rmcBlockQuantity3 is zero or rmcBlockIndex3 + rmcBlockQuantity3 - 1 is greater than the table's maximum number of rows
9) rmcBlockIndex4 is zero or is greater than the table's maximum number of rows
10) rmcBlockQuantity4 is zero or rmcBlockIndex4 + rmcBlockQuantity4 - 1 is greater than the table's maximum number of rows
11) rmcBlockIndex5 is zero or is greater than the table's maximum number of rows
12) rmcBlockQuantity5 is zero or rmcBlockIndex5 + rmcBlockQuantity5 - 1 is greater than the table's maximum number of rows
13) if the SET length is zero or incorrect for rmcBlockDataType & rmcBlockDataID
14) if the SET (SEQUENCE OF) value is incorrect.
When this validity check fails, rmcBlockErrorStatus shall be set equal to the Bullet Value above that generated the error. Because of SNMP, it cannot be determined in advance which error of multiple, simultaneous errors will be reported.

A SET that includes an unsupported value for a supported data element shall return an Error Status of badValue(3) and rmcBlockErrorStatus shall be set equal to:
(data Sequence # * 100) + data Element #

A SET that includes a non-zero or non-null value in the position of an unsupported data element shall return an Error Status of badValue(3) and rmcBlockErrorStatus shall be set equal to:
(data Sequence # * 100) + data Element #

A GET on this object shall utilize values currently in rmcBlockGetControl to define the data to be returned. When rmcBlockGetControl has invalid data, an Error Status of badValue(3) shall be returned.

A GET shall return a zero or null value in the position of an unsupported object.

<Object Identifier> 1.3.6.1.4.1.1206.4.2.2.7.2"
::= { rmcBlock 2 }

--3.8.3	RMC Block Error Status
rmcBlockErrorStatus   OBJECT-TYPE
SYNTAX   INTEGER (0..65535)
ACCESS   read-only
STATUS   mandatory
DESCRIPTION
"<Definition> This object defines the data element within rmcBlockGetControl or rmcBlockData objects that caused a badValue(3) Error Status. 
This object should equal zero after any successful SET to rmcBlockGetControl or rmcBlockData.

<Object Identifier> 1.3.6.1.4.1.1206.4.2.2.7.3"
::= { rmcBlock 3 }

END
